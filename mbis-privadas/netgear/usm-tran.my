USM-TARGET-TAG-MIB DEFINITIONS ::= BEGIN

    IMPORTS
        snmpResearchMIBs
            FROM SNMP-RESEARCH-MIB
        MODULE-IDENTITY,
        OBJECT-TYPE
            FROM SNMPv2-SMI
        SnmpTagValue
            FROM SNMP-TARGET-MIB
        usmUserEntry
            FROM SNMP-USER-BASED-SM-MIB 
        MODULE-COMPLIANCE,
        OBJECT-GROUP
            FROM SNMPv2-CONF;


    usmTargetTagMIB MODULE-IDENTITY
        LAST-UPDATED "9801160000"
        ORGANIZATION "SNMP Research, Inc."
        CONTACT-INFO
                      ""
        DESCRIPTION
              ""
        ::= { snmpResearchMIBs 35 }


    --
    -- The usmTargetTagObjects Group
    --

    usmTargetTagObjects OBJECT IDENTIFIER ::=
        { usmTargetTagMIB 1 }
    usmTargetTagConformance OBJECT IDENTIFIER ::=
        { usmTargetTagMIB 3 }

    --
    -- The usmTargetTagTable
    --

    usmTargetTagTable OBJECT-TYPE
        SYNTAX       SEQUENCE OF UsmTargetTagEntry
        MAX-ACCESS   not-accessible
        STATUS       current
        DESCRIPTION
              "Table to add an SnmpTagValue to the usmUserTable."
        ::= { usmTargetTagObjects 1 }

    usmTargetTagEntry OBJECT-TYPE
        SYNTAX       UsmTargetTagEntry
        MAX-ACCESS   not-accessible
        STATUS       current
        DESCRIPTION
                   "Adds an SnmpTagValue to a usmUserEntry."
        AUGMENTS { usmUserEntry }
        ::= { usmTargetTagTable 1 }

    UsmTargetTagEntry ::= SEQUENCE {
        usmTargetTag     SnmpTagValue
    }

    usmTargetTag OBJECT-TYPE
        SYNTAX       SnmpTagValue
        MAX-ACCESS   read-create
        STATUS       current
        DESCRIPTION
              "This object specifies a set of transport endpoints from which
              an agent will accept management requests.  If a management
              request generated by this user is received on a transport
              endpoint other than the transport endpoints identified
              by this object, the request is deemed unauthentic.

              The transports identified by this object are normally
              specified in the snmpTargetAddrTable, and are selected
              using tag matching as specified in the SNMPv3 Applications
              document (rfc2263).

              If the value of this object has zero-length, then
              transport endpoints are not checked when authenticating
              messages generated by this user."
         DEFVAL { ''H }     -- the empty string
        ::= { usmTargetTagEntry 1 }

usmTargetTagCompliances   OBJECT IDENTIFIER ::= { usmTargetTagConformance 1 }
usmTargetTagGroups        OBJECT IDENTIFIER ::= { usmTargetTagConformance 2 }
 
usmTargetTagGroup OBJECT-GROUP
    OBJECTS {
        usmTargetTag
    }
    STATUS       current
    DESCRIPTION
        "usmTargetTag group"
    ::= { usmTargetTagGroups 1 }

END
