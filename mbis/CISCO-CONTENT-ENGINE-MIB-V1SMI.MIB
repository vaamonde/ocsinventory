-- MIB file created 27-Nov-2002 19:43:51, by
--   SMICng version 2.2.11-beta(PRO)(Solaris), January 20, 2001. Enterprise key cisco.com

CISCO-CONTENT-ENGINE-MIB DEFINITIONS ::= BEGIN

-- From file: "CISCO-CONTENT-ENGINE-MIB.my"
-- Compile options "4 7 F H N W 03 06 0B 0G 0N 0T"

IMPORTS
--  Unsigned32
--          FROM CISCO-TC
    ciscoMgmt
            FROM CISCO-SMI
    Counter, Gauge
            FROM RFC1155-SMI
    OBJECT-TYPE
            FROM RFC-1212
    TRAP-TYPE
            FROM RFC-1215;

ciscoContentEngineMIB OBJECT IDENTIFIER ::= { ciscoMgmt 178 }
-- MODULE-IDENTITY
--  LastUpdated
--    200205200000Z
--  OrgName
--    Cisco Systems, Inc.
--  ContactInfo
--    Cisco Systems Customer Service
--     Postal: 170 W Tasman Drive
--         San Jose, CA 95134-1706
--         USA
--         Tel: +1 800 553-NETS
--         E-mail: cs-webcache@cisco.com
--  Descr
--    The MIB module for the Cisco Content Engine from
--     Cisco Systems, Inc.
--  RevDate
--    200205200000Z
--  RevDescr
--    Added cceWmtGroup, cceCseGroup, and cceRpGroup groups.
--  RevDate
--    200002100000Z
--  RevDescr
--    Initial version of this MIB module.

ciscoContentEngineMIBObjects OBJECT IDENTIFIER ::= { ciscoContentEngineMIB 1 }
cceHttpGroup    OBJECT IDENTIFIER ::= { ciscoContentEngineMIBObjects 1 }
cceWmtGroup     OBJECT IDENTIFIER ::= { ciscoContentEngineMIBObjects 2 }
cceCseGroup     OBJECT IDENTIFIER ::= { ciscoContentEngineMIBObjects 3 }
cceRpGroup      OBJECT IDENTIFIER ::= { ciscoContentEngineMIBObjects 4 }
cceHttpRequests OBJECT IDENTIFIER ::= { cceHttpGroup 1 }
cceHttpPerf     OBJECT IDENTIFIER ::= { cceHttpGroup 2 }
cceWmtRequests  OBJECT IDENTIFIER ::= { cceWmtGroup 1 }
cceWmtHCRequests OBJECT IDENTIFIER ::= { cceWmtGroup 2 }
cceWmtPerf      OBJECT IDENTIFIER ::= { cceWmtGroup 3 }
cceCseRequests  OBJECT IDENTIFIER ::= { cceCseGroup 1 }
cceCseHCRequests OBJECT IDENTIFIER ::= { cceCseGroup 2 }
cceCsePerf      OBJECT IDENTIFIER ::= { cceCseGroup 3 }
cceRpRequests   OBJECT IDENTIFIER ::= { cceRpGroup 1 }
cceRpHCRequests OBJECT IDENTIFIER ::= { cceRpGroup 2 }
ciscoContentEngineMIBNotificationPrefix OBJECT IDENTIFIER ::= { ciscoContentEngineMIB 2 }
ciscoContentEngineMIBNotifications OBJECT IDENTIFIER ::= { ciscoContentEngineMIBNotificationPrefix 0 }
ciscoContentEngineMIBConformance OBJECT IDENTIFIER ::= { ciscoContentEngineMIB 3 }
ciscoContentEngineMIBCompliances OBJECT IDENTIFIER ::= { ciscoContentEngineMIBConformance 1 }
ciscoContentEngineMIBGroups OBJECT IDENTIFIER ::= { ciscoContentEngineMIBConformance 2 }

cceHttpRequestsTotal OBJECT-TYPE
    SYNTAX Counter
    ACCESS read-only
    STATUS mandatory
    DESCRIPTION
        "Total number of end-user requests the HTTP proxy
        has received."
    ::= { cceHttpRequests 1 }

cceHttpRequestsNoCacheTotal OBJECT-TYPE
    SYNTAX Counter
    ACCESS read-only
    STATUS mandatory
    DESCRIPTION
        "Total number of end-user requests the HTTP proxy
        has received which contain a header directive indicating 
        that the object cannot be cached."
    ::= { cceHttpRequests 2 }

cceHttpRequestsClientErrorTotal OBJECT-TYPE
    SYNTAX Counter
    ACCESS read-only
    STATUS mandatory
    DESCRIPTION
        "Total number of times the HTTP proxy has failed to fulfill 
         a request due to errors caused by client connections."
    ::= { cceHttpRequests 3 }

cceHttpRequestsServerErrorTotal OBJECT-TYPE
    SYNTAX Counter
    ACCESS read-only
    STATUS mandatory
    DESCRIPTION
        "Total number of times the HTTP proxy has failed to fulfill 
         a request due to errors while fetching objects not in cache
         from remote servers."
    ::= { cceHttpRequests 4 }

cceHttpRequestsBlocked OBJECT-TYPE
    SYNTAX Counter
    ACCESS read-only
    STATUS mandatory
    DESCRIPTION
        "The number of times the HTTP proxy has blocked a request
         due to URL filtering or rules template blocking."
    ::= { cceHttpRequests 5 }

cceHttpRequestsHits OBJECT-TYPE
    SYNTAX Counter
    ACCESS read-only
    STATUS mandatory
    DESCRIPTION
        "Total number of end-user requests whose response body was
        retrieved from the populated cache of the HTTP proxy."
    ::= { cceHttpRequests 6 }

cceHttpRequestsMisses OBJECT-TYPE
    SYNTAX Counter
    ACCESS read-only
    STATUS mandatory
    DESCRIPTION
        "Total number of end-user requests whose response body is  
        retrieved from remote servers."
    ::= { cceHttpRequests 7 }

cceHttpRequestsBytesServedHits OBJECT-TYPE
    SYNTAX Counter
    ACCESS read-only
    STATUS mandatory
    DESCRIPTION
        "Total number of bytes in the response bodies the HTTP proxy
        retrieved directly from its populated cache."
    ::= { cceHttpRequests 8 }

cceHttpRequestsBytesServedMisses OBJECT-TYPE
    SYNTAX Counter
    ACCESS read-only
    STATUS mandatory
    DESCRIPTION
        "Total number of bytes in the response bodies the HTTP proxy  
         retrieved from remote servers."
    ::= { cceHttpRequests 9 }

cceHttpRequestsImsInmTotalCache OBJECT-TYPE
    SYNTAX Counter
    ACCESS read-only
    STATUS mandatory
    DESCRIPTION
        "Total number of If-Modified-Since (IMS) and If-Not-Matched
        (INM) requests from the client served from the populated
        cache of the HTTP proxy without revalidation."
    ::= { cceHttpRequests 10 }

cceHttpRequestsImsInmTotalReval OBJECT-TYPE
    SYNTAX Counter
    ACCESS read-only
    STATUS mandatory
    DESCRIPTION
        "Total number of If-Modified-Since (IMS) and If-Not-Matched
         (INM) requests from the client served from the populated
         cache of the HTTP proxy and revalidated with an IMS to the
         server."
    ::= { cceHttpRequests 11 }

cceHttpRequestsBytesClientIn OBJECT-TYPE
    SYNTAX Counter
    ACCESS read-only
    STATUS mandatory
    DESCRIPTION
        "Total number of bytes received by the HTTP proxy from
         clients."
    ::= { cceHttpRequests 12 }

cceHttpRequestsBytesClientOut OBJECT-TYPE
    SYNTAX Counter
    ACCESS read-only
    STATUS mandatory
    DESCRIPTION
        "Total number of bytes delivered by the HTTP proxy to
         clients."
    ::= { cceHttpRequests 13 }

cceHttpRequestsBytesServerIn OBJECT-TYPE
    SYNTAX Counter
    ACCESS read-only
    STATUS mandatory
    DESCRIPTION
        "Total number of bytes received by the HTTP proxy from
         remote servers."
    ::= { cceHttpRequests 14 }

cceHttpRequestsBytesServerOut OBJECT-TYPE
    SYNTAX Counter
    ACCESS read-only
    STATUS mandatory
    DESCRIPTION
        "Total number of bytes transmitted by the HTTP proxy
         to remote servers."
    ::= { cceHttpRequests 15 }

cceHttpHCRequestsTotal OBJECT-TYPE
    SYNTAX --?? syntax is not convertable to SMIv1
           Counter
    ACCESS read-only
    STATUS mandatory
    DESCRIPTION
        "Total number of end-user requests the HTTP proxy
         has received.  This object is a 64-bit
         version of cceHttpRequestsTotal."
    ::= { cceHttpRequests 16 }

cceHttpHCRequestsNoCacheTotal OBJECT-TYPE
    SYNTAX --?? syntax is not convertable to SMIv1
           Counter
    ACCESS read-only
    STATUS mandatory
    DESCRIPTION
        "Total number of end-user requests the HTTP proxy
         has received which contain a header directive
         indicating that the object cannot be cached.
         This object is a 64-bit version of
         cceHttpRequestsNoCacheTotal."
    ::= { cceHttpRequests 17 }

cceHttpHCRequestsClientErrorTotal OBJECT-TYPE
    SYNTAX --?? syntax is not convertable to SMIv1
           Counter
    ACCESS read-only
    STATUS mandatory
    DESCRIPTION
        "Total number of times the HTTP proxy has failed to fulfill 
         a request due to errors caused by client connections.
         This object is a 64-bit version of
         cceHttpRequestsClientErrorTotal."
    ::= { cceHttpRequests 18 }

cceHttpHCRequestsServerErrorTotal OBJECT-TYPE
    SYNTAX --?? syntax is not convertable to SMIv1
           Counter
    ACCESS read-only
    STATUS mandatory
    DESCRIPTION
        "Total number of times the HTTP proxy has failed to fulfill 
         a request due to errors while fetching objects not in cache
         from remote servers.  This object is a 64-bit version of
         cceHttpRequestsServerErrorTotal."
    ::= { cceHttpRequests 19 }

cceHttpHCRequestsBlocked OBJECT-TYPE
    SYNTAX --?? syntax is not convertable to SMIv1
           Counter
    ACCESS read-only
    STATUS mandatory
    DESCRIPTION
        "The number of times the HTTP proxy has blocked a request
         due to URL filtering or rules template blocking.
         This object is a 64-bit version of cceHttpRequestsBlocked."
    ::= { cceHttpRequests 20 }

cceHttpHCRequestsHits OBJECT-TYPE
    SYNTAX --?? syntax is not convertable to SMIv1
           Counter
    ACCESS read-only
    STATUS mandatory
    DESCRIPTION
        "Total number of end-user requests whose response body was
         retrieved from the populated cache of the HTTP proxy.
         This object is a 64-bit version of cceHttpRequestsHits."
    ::= { cceHttpRequests 21 }

cceHttpHCRequestsMisses OBJECT-TYPE
    SYNTAX --?? syntax is not convertable to SMIv1
           Counter
    ACCESS read-only
    STATUS mandatory
    DESCRIPTION
        "Total number of end-user requests whose response body is  
         retrieved from remote servers.  This object is a 64-bit
         version of cceHttpRequestsMisses."
    ::= { cceHttpRequests 22 }

cceHttpHCRequestsBytesServedHits OBJECT-TYPE
    SYNTAX --?? syntax is not convertable to SMIv1
           Counter
    ACCESS read-only
    STATUS mandatory
    DESCRIPTION
        "Total number of bytes in the response bodies the HTTP proxy
         retrieved directly from its populated cache.  This object
         is a 64-bit version of cceHttpRequestsBytesServedHits."
    ::= { cceHttpRequests 23 }

cceHttpHCRequestsBytesServedMisses OBJECT-TYPE
    SYNTAX --?? syntax is not convertable to SMIv1
           Counter
    ACCESS read-only
    STATUS mandatory
    DESCRIPTION
        "Total number of bytes in the response bodies the HTTP proxy
        retrieved from remote servers. This object is a 64-bit
        version of cceHttpRequestsBytesServedMisses."
    ::= { cceHttpRequests 24 }

cceHttpHCRequestsImsInmTotalCache OBJECT-TYPE
    SYNTAX --?? syntax is not convertable to SMIv1
           Counter
    ACCESS read-only
    STATUS mandatory
    DESCRIPTION
        "Total number of If-Modified-Since (IMS) and If-Not-Matched
         (INM) requests from the client served from the populated
         cache of the HTTP proxy without revalidation. This object
         is a 64-bit version of cceHttpRequestsImsInmTotalCache."
    ::= { cceHttpRequests 25 }

cceHttpHCRequestsImsInmTotalReval OBJECT-TYPE
    SYNTAX --?? syntax is not convertable to SMIv1
           Counter
    ACCESS read-only
    STATUS mandatory
    DESCRIPTION
        "Total number of If-Modified-Since (IMS) and If-Not-Matched
         (INM) requests from the client served from the populated
         cache of the HTTP proxy and revalidated with an IMS to the
         server.  This object is a 64-bit version of
         cceHttpRequestsImsInmTotalReval."
    ::= { cceHttpRequests 26 }

cceHttpHCRequestsBytesClientIn OBJECT-TYPE
    SYNTAX --?? syntax is not convertable to SMIv1
           Counter
    ACCESS read-only
    STATUS mandatory
    DESCRIPTION
        "Total number of bytes received by the HTTP proxy from
         clients.  This object is a 64-bit version of
         cceHttpRequestsBytesClientIn."
    ::= { cceHttpRequests 27 }

cceHttpHCRequestsBytesClientOut OBJECT-TYPE
    SYNTAX --?? syntax is not convertable to SMIv1
           Counter
    ACCESS read-only
    STATUS mandatory
    DESCRIPTION
        "Total number of bytes delivered by the HTTP proxy to
         clients.  This object is a 64-bit version of
         cceHttpRequestsBytesClientOut."
    ::= { cceHttpRequests 28 }

cceHttpHCRequestsBytesServerIn OBJECT-TYPE
    SYNTAX --?? syntax is not convertable to SMIv1
           Counter
    ACCESS read-only
    STATUS mandatory
    DESCRIPTION
        "Total number of bytes received by the HTTP proxy from
         remote servers.  This object is a 64-bit version of
         cceHttpRequestsBytesServerIn."
    ::= { cceHttpRequests 29 }

cceHttpHCRequestsBytesServerOut OBJECT-TYPE
    SYNTAX --?? syntax is not convertable to SMIv1
           Counter
    ACCESS read-only
    STATUS mandatory
    DESCRIPTION
        "Total number of bytes transmitted by the HTTP proxy
         to remote servers.  This object is a 64-bit version of
         cceHttpRequestsBytesServerOut."
    ::= { cceHttpRequests 30 }

cceHttpPerfSamplingTime OBJECT-TYPE
    SYNTAX Gauge(0..4294967295)
--  Units
--    seconds
    ACCESS read-only
    STATUS mandatory
    DESCRIPTION
        "Number of seconds in the last sampling time interval
         used to calculate the value of the cceHttpPerfReqPerSec
         and cceHttpPerfBytesPerSec objects."
    ::= { cceHttpPerf 1 }

cceHttpPerfReqPerSec OBJECT-TYPE
    SYNTAX Gauge(0..4294967295)
    ACCESS read-only
    STATUS mandatory
    DESCRIPTION
        "Number of requests per second the HTTP proxy
         has been servicing in the last sampling time."
    ::= { cceHttpPerf 2 }

cceHttpPerfBytesPerSec OBJECT-TYPE
    SYNTAX Gauge(0..4294967295)
--  Units
--    bytes-per-second
    ACCESS read-only
    STATUS mandatory
    DESCRIPTION
        "Bytes per second served in the last sampling time."
    ::= { cceHttpPerf 3 }

cceHttpPerfServiceTime OBJECT-TYPE
    SYNTAX Gauge(0..4294967295)
--  Units
--    milliseconds-per-req
    ACCESS read-only
    STATUS mandatory
    DESCRIPTION
        "Average duration of each connection serviced by the 
         HTTP proxy."
    ::= { cceHttpPerf 4 }

cceHttpPerfHitServiceTime OBJECT-TYPE
    SYNTAX Gauge(0..4294967295)
--  Units
--    milliseconds-per-req
    ACCESS read-only
    STATUS mandatory
    DESCRIPTION
        "Average duration required for the HTTP proxy to send a
         hit response.  A hit response is a response for which
         the object can be serviced from the populated cache of
         the HTTP proxy."
    ::= { cceHttpPerf 5 }

cceHttpPerfMissServiceTime OBJECT-TYPE
    SYNTAX Gauge(0..4294967295)
--  Units
--    milliseconds-per-req
    ACCESS read-only
    STATUS mandatory
    DESCRIPTION
        "Average duration required for the HTTP proxy to send a
         miss response.  A miss response is a response for which
         the object cannot be serviced from the populated cache
         of the HTTP proxy."
    ::= { cceHttpPerf 6 }

cceHttpPerfObjectSize OBJECT-TYPE
    SYNTAX Gauge(0..4294967295)
--  Units
--    bytes
    ACCESS read-only
    STATUS mandatory
    DESCRIPTION
        "Average size of the object served from the HTTP proxy."
    ::= { cceHttpPerf 7 }

cceHttpPerfCpuLoad OBJECT-TYPE
    SYNTAX Gauge(0..100)
--  Units
--    percentage
    ACCESS read-only
    STATUS mandatory
    DESCRIPTION
        "Percentage of CPU load for the last 4 second sampling
         time interval."
    ::= { cceHttpPerf 8 }

cceWmtTotalRequests OBJECT-TYPE
    SYNTAX Counter
    ACCESS read-only
    STATUS mandatory
    DESCRIPTION
        "Total number of end-user requests the WMT proxy/server
         has received."
    ::= { cceWmtRequests 1 }

cceWmtTotalClientErrors OBJECT-TYPE
    SYNTAX Counter
    ACCESS read-only
    STATUS mandatory
    DESCRIPTION
        "Total number of times the WMT proxy/server has failed to 
        fulfill a request due to errors caused by client connections."
    ::= { cceWmtRequests 2 }

cceWmtTotalServerErrors OBJECT-TYPE
    SYNTAX Counter
    ACCESS read-only
    STATUS mandatory
    DESCRIPTION
        "Total number of times the WMT proxy has failed to fulfill
         a request due to errors while fetching objects not in cache
         from remote servers."
    ::= { cceWmtRequests 3 }

cceWmtBlockedRequests OBJECT-TYPE
    SYNTAX Counter
    ACCESS read-only
    STATUS mandatory
    DESCRIPTION
        "The number of times the WMT proxy/server has blocked a request
        due to URL filtering or rules template blocking."
    ::= { cceWmtRequests 4 }

cceWmtRequestHits OBJECT-TYPE
    SYNTAX Counter
    ACCESS read-only
    STATUS mandatory
    DESCRIPTION
        "Total number of end-user requests whose response body was
         retrieved from the populated cache of the WMT proxy."
    ::= { cceWmtRequests 5 }

cceWmtRequestMisses OBJECT-TYPE
    SYNTAX Counter
    ACCESS read-only
    STATUS mandatory
    DESCRIPTION
        "Total number of end-user requests whose response body is
         retrieved from remote servers."
    ::= { cceWmtRequests 6 }

cceWmtRequestHitsBytesServed OBJECT-TYPE
    SYNTAX Counter
--  Units
--    Bytes
    ACCESS read-only
    STATUS mandatory
    DESCRIPTION
        "Total number of bytes in the response bodies the WMT proxy
        retrieved directly from its populated cache."
    ::= { cceWmtRequests 7 }

cceWmtRequestMissesBytesServed OBJECT-TYPE
    SYNTAX Counter
--  Units
--    Bytes
    ACCESS read-only
    STATUS mandatory
    DESCRIPTION
        "Total number of bytes in the response bodies the WMT proxy 
        retrieved from remote servers."
    ::= { cceWmtRequests 8 }

cceWmtTotalLiveRequests OBJECT-TYPE
    SYNTAX Counter
    ACCESS read-only
    STATUS mandatory
    DESCRIPTION
        "Total number of end-user live requests the WMT proxy/server
         has received."
    ::= { cceWmtRequests 9 }

cceWmtLiveRequestBytes OBJECT-TYPE
    SYNTAX Counter
--  Units
--    Bytes
    ACCESS read-only
    STATUS mandatory
    DESCRIPTION
        "Total number of live splitting bytes served from the WMT
        proxy/server."
    ::= { cceWmtRequests 10 }

cceWmtTotalMmsuRequests OBJECT-TYPE
    SYNTAX Counter
    ACCESS read-only
    STATUS mandatory
    DESCRIPTION
        "Total number of end-user 
        MMSU (Microsoft Media Service over UDP)
        requests the WMT proxy/server has received."
    ::= { cceWmtRequests 11 }

cceWmtTotalMmsuBytes OBJECT-TYPE
    SYNTAX Counter
--  Units
--    Bytes
    ACCESS read-only
    STATUS mandatory
    DESCRIPTION
        "Total number of bytes served through MMSU from WMT
        proxy/server."
    ::= { cceWmtRequests 12 }

cceWmtTotalMmstRequests OBJECT-TYPE
    SYNTAX Counter
    ACCESS read-only
    STATUS mandatory
    DESCRIPTION
        "Total number of end-user 
        MMST (Microsoft Media Service over TCP) 
        requests the WMT proxy/server has received."
    ::= { cceWmtRequests 13 }

cceWmtTotalMmstBytes OBJECT-TYPE
    SYNTAX Counter
--  Units
--    Bytes
    ACCESS read-only
    STATUS mandatory
    DESCRIPTION
        "Total number of bytes served through MMST from WMT 
        proxy/server."
    ::= { cceWmtRequests 14 }

cceWmtTotalHttpRequests OBJECT-TYPE
    SYNTAX Counter
    ACCESS read-only
    STATUS mandatory
    DESCRIPTION
        "Total number of end-user HTTP requests the WMT proxy/server 
        has received."
    ::= { cceWmtRequests 15 }

cceWmtTotalHttpBytes OBJECT-TYPE
    SYNTAX Counter
--  Units
--    Bytes
    ACCESS read-only
    STATUS mandatory
    DESCRIPTION
        "Total number of bytes served through HTTP from WMT
        proxy/server."
    ::= { cceWmtRequests 16 }

cceWmtTotalMulticastBytes OBJECT-TYPE
    SYNTAX Counter
--  Units
--    Bytes
    ACCESS read-only
    STATUS mandatory
    DESCRIPTION
        "Total number of bytes served through multicast from 
        WMT server."
    ::= { cceWmtRequests 17 }

cceWmtHCRequestHitsBytesServed OBJECT-TYPE
    SYNTAX --?? syntax is not convertable to SMIv1
           Counter
--  Units
--    Bytes
    ACCESS read-only
    STATUS mandatory
    DESCRIPTION
        "Total number of bytes in the response bodies the WMT proxy
         retrieved directly from its populated cache."
    ::= { cceWmtHCRequests 1 }

cceWmtHCRequestMissesBytesServed OBJECT-TYPE
    SYNTAX --?? syntax is not convertable to SMIv1
           Counter
--  Units
--    Bytes
    ACCESS read-only
    STATUS mandatory
    DESCRIPTION
        "Total number of bytes in the response bodies the WMT proxy
         retrieved from remote servers."
    ::= { cceWmtHCRequests 2 }

cceWmtHCLiveRequestBytes OBJECT-TYPE
    SYNTAX --?? syntax is not convertable to SMIv1
           Counter
--  Units
--    Bytes
    ACCESS read-only
    STATUS mandatory
    DESCRIPTION
        "Total number of live splitting bytes served from the WMT
        proxy/server."
    ::= { cceWmtHCRequests 3 }

cceWmtHCTotalMmsuBytes OBJECT-TYPE
    SYNTAX --?? syntax is not convertable to SMIv1
           Counter
--  Units
--    Bytes
    ACCESS read-only
    STATUS mandatory
    DESCRIPTION
        "Total number of bytes served through MMSU from WMT
         proxy/server."
    ::= { cceWmtHCRequests 4 }

cceWmtHCTotalMmstBytes OBJECT-TYPE
    SYNTAX --?? syntax is not convertable to SMIv1
           Counter
--  Units
--    Bytes
    ACCESS read-only
    STATUS mandatory
    DESCRIPTION
        "Total number of bytes served through MMST from WMT
         proxy/server."
    ::= { cceWmtHCRequests 5 }

cceWmtHCTotalHttpBytes OBJECT-TYPE
    SYNTAX --?? syntax is not convertable to SMIv1
           Counter
--  Units
--    Bytes
    ACCESS read-only
    STATUS mandatory
    DESCRIPTION
        "Total number of bytes served through HTTP from WMT
        proxy/server."
    ::= { cceWmtHCRequests 6 }

cceWmtHCTotalMulticastBytes OBJECT-TYPE
    SYNTAX --?? syntax is not convertable to SMIv1
           Counter
--  Units
--    Bytes
    ACCESS read-only
    STATUS mandatory
    DESCRIPTION
        "Total number of bytes served through multicast 
         from WMT server."
    ::= { cceWmtHCRequests 7 }

cceWmtPerfConcurrentRequests OBJECT-TYPE
    SYNTAX Gauge
    ACCESS read-only
    STATUS mandatory
    DESCRIPTION
        "Number of concurrent requests the WMT proxy/server
         is servicing at the current time."
    ::= { cceWmtPerf 1 }

cceWmtPerfKbitsPerSec OBJECT-TYPE
    SYNTAX Gauge
--  Units
--    Kbits-per-sec
    ACCESS read-only
    STATUS mandatory
    DESCRIPTION
        "Kilobits per second to end-users served at the current time."
    ::= { cceWmtPerf 2 }

cceWmtPerfMulticastSessions OBJECT-TYPE
    SYNTAX Gauge
--  Units
--    sessions
    ACCESS read-only
    STATUS mandatory
    DESCRIPTION
        "Number of concurrent active multicast sessions at 
        the current time."
    ::= { cceWmtPerf 3 }

cceWmtPerfMulticastKbitsPerSec OBJECT-TYPE
    SYNTAX Gauge
--  Units
--    Kbits-per-sec
    ACCESS read-only
    STATUS mandatory
    DESCRIPTION
        "Kilobits per second served through multicast at current time."
    ::= { cceWmtPerf 4 }

cceCseTotalRequests OBJECT-TYPE
    SYNTAX Counter
    ACCESS read-only
    STATUS mandatory
    DESCRIPTION
        "Total number of end-user requests the 
        Cisco Streaming Engine has received."
    ::= { cceCseRequests 1 }

cceCseRequestPacketsServed OBJECT-TYPE
    SYNTAX Counter
--  Units
--    packets
    ACCESS read-only
    STATUS mandatory
    DESCRIPTION
        "Total number of packets in the response served 
        by the Cisco Streaming Engine."
    ::= { cceCseRequests 2 }

cceCseRequestBytesServed OBJECT-TYPE
    SYNTAX Counter
--  Units
--    Bytes
    ACCESS read-only
    STATUS mandatory
    DESCRIPTION
        "Total number of bytes in the response served by the Cisco
        Streaming Engine."
    ::= { cceCseRequests 3 }

cceCseHCRequestPacketsServed OBJECT-TYPE
    SYNTAX --?? syntax is not convertable to SMIv1
           Counter
--  Units
--    packets
    ACCESS read-only
    STATUS mandatory
    DESCRIPTION
        "Total number of packets in the response served by
        the Cisco Streaming Engine."
    ::= { cceCseHCRequests 1 }

cceCseHCRequestBytesServed OBJECT-TYPE
    SYNTAX --?? syntax is not convertable to SMIv1
           Counter
--  Units
--    Bytes
    ACCESS read-only
    STATUS mandatory
    DESCRIPTION
        "Total number of bytes in the response served by 
        the Cisco Streaming Engine."
    ::= { cceCseHCRequests 2 }

cceCsePerfConcurrentReqs OBJECT-TYPE
    SYNTAX Gauge
    ACCESS read-only
    STATUS mandatory
    DESCRIPTION
        "Number of concurrent requests the Cisco Streaming Engine
         is servicing at the current time."
    ::= { cceCsePerf 1 }

cceCsePerfCurrentBandwidth OBJECT-TYPE
    SYNTAX Gauge
--  Units
--    Kbits
    ACCESS read-only
    STATUS mandatory
    DESCRIPTION
        "The bandwidth reserved(Kilobits) for the current requests
        the Cisco Streaming Engine is serving."
    ::= { cceCsePerf 2 }

cceRpTotalHits OBJECT-TYPE
    SYNTAX Counter
    ACCESS read-only
    STATUS mandatory
    DESCRIPTION
        "Total number of end-user requests whose response body
        was retrieved from the populated cache of the Real Proxy."
    ::= { cceRpRequests 1 }

cceRpTotalMisses OBJECT-TYPE
    SYNTAX Counter
    ACCESS read-only
    STATUS mandatory
    DESCRIPTION
        "Total number of end-user requests whose response body was 
        retrieved from remote servers."
    ::= { cceRpRequests 2 }

cceRpTotalVodPassThroughs OBJECT-TYPE
    SYNTAX Counter
    ACCESS read-only
    STATUS mandatory
    DESCRIPTION
        "Total number of end-user VOD (Video On Demand) requests 
        which cannot be cached by the Real Proxy."
    ::= { cceRpRequests 3 }

cceRpTotalLiveSplitReqs OBJECT-TYPE
    SYNTAX Counter
    ACCESS read-only
    STATUS mandatory
    DESCRIPTION
        "Total number of end-user live requests for Real Proxy."
    ::= { cceRpRequests 4 }

cceRpTotalLivePassThruSplitReqs OBJECT-TYPE
    SYNTAX Counter
    ACCESS read-only
    STATUS mandatory
    DESCRIPTION
        "Total number of end-user live requests, which Real Proxy 
        cannot split."
    ::= { cceRpRequests 5 }

cceRpTotalIncomingBytes OBJECT-TYPE
    SYNTAX Counter
--  Units
--    Bytes
    ACCESS read-only
    STATUS mandatory
    DESCRIPTION
        "Total bytes received by the Real Proxy from remote servers."
    ::= { cceRpRequests 6 }

cceRpTotalOutgoingBytes OBJECT-TYPE
    SYNTAX Counter
--  Units
--    Bytes
    ACCESS read-only
    STATUS mandatory
    DESCRIPTION
        "Total bytes sent by the Real Proxy to end-users."
    ::= { cceRpRequests 7 }

cceRpHCTotalHits OBJECT-TYPE
    SYNTAX --?? syntax is not convertable to SMIv1
           Counter
    ACCESS read-only
    STATUS mandatory
    DESCRIPTION
        "Total number of end-user requests whose response body
        was retrieved from the populated cache of the Real Proxy."
    ::= { cceRpHCRequests 1 }

cceRpHCTotalMisses OBJECT-TYPE
    SYNTAX --?? syntax is not convertable to SMIv1
           Counter
    ACCESS read-only
    STATUS mandatory
    DESCRIPTION
        "Total number of end-user requests whose response body was 
        retrieved from remote servers."
    ::= { cceRpHCRequests 2 }

cceRpHCTotalVodPassThroughs OBJECT-TYPE
    SYNTAX --?? syntax is not convertable to SMIv1
           Counter
    ACCESS read-only
    STATUS mandatory
    DESCRIPTION
        "Total number of end-user VOD (Video On Demand) requests 
        which cannot be cached by the Real Proxy."
    ::= { cceRpHCRequests 3 }

cceRpHCTotalLiveSplitReqs OBJECT-TYPE
    SYNTAX --?? syntax is not convertable to SMIv1
           Counter
    ACCESS read-only
    STATUS mandatory
    DESCRIPTION
        "Total number of end-user live requests for Real Proxy."
    ::= { cceRpHCRequests 4 }

cceRpHCTotalLivePassThruSplitReqs OBJECT-TYPE
    SYNTAX --?? syntax is not convertable to SMIv1
           Counter
    ACCESS read-only
    STATUS mandatory
    DESCRIPTION
        "Total number of end-user live requests, which Real Proxy 
        cannot split."
    ::= { cceRpHCRequests 5 }

cceRpHCTotalIncomingBytes OBJECT-TYPE
    SYNTAX --?? syntax is not convertable to SMIv1
           Counter
--  Units
--    Bytes
    ACCESS read-only
    STATUS mandatory
    DESCRIPTION
        "Total bytes received by the Real Proxy from remote servers."
    ::= { cceRpHCRequests 6 }

cceRpHCTotalOutgoingBytes OBJECT-TYPE
    SYNTAX --?? syntax is not convertable to SMIv1
           Counter
--  Units
--    Bytes
    ACCESS read-only
    STATUS mandatory
    DESCRIPTION
        "Total bytes sent by the Real Proxy to end-users."
    ::= { cceRpHCRequests 7 }

ciscoContentEngineReadDiskError TRAP-TYPE
-- Reverse mappable trap
    ENTERPRISE ciscoContentEngineMIBNotificationPrefix
--  Status
--    mandatory
    DESCRIPTION
        "First read error occurred on the disk that is being
         accessed.  Additional information about the error
         is logged to syslog."
    ::= 1

ciscoContentEngineWriteDiskError TRAP-TYPE
-- Reverse mappable trap
    ENTERPRISE ciscoContentEngineMIBNotificationPrefix
--  Status
--    mandatory
    DESCRIPTION
        "First write error occurred on the disk that is being
         accessed.  Additional information about the error
         is logged to syslog."
    ::= 2

ciscoContentEngineWriteTransFailed TRAP-TYPE
-- Reverse mappable trap
    ENTERPRISE ciscoContentEngineMIBNotificationPrefix
--  Status
--    mandatory
    DESCRIPTION
        "Failed writing to working transaction log located in
         /local1/working.log.  Possible causes are system
         errors or the log having been removed."
    ::= 3

ciscoContentEngineDataDiskFailed TRAP-TYPE
-- Reverse mappable trap
    ENTERPRISE ciscoContentEngineMIBNotificationPrefix
--  Status
--    mandatory
    DESCRIPTION
        "A Content Engine data drive failed.  Additional
         information about the error is logged to syslog."
    ::= 4

ciscoContentEngineOverloadBypass TRAP-TYPE
-- Reverse mappable trap
    ENTERPRISE ciscoContentEngineMIBNotificationPrefix
--  Status
--    mandatory
    DESCRIPTION
        "A high watermark of percentage of capacity for transparent
         requests redirected to the Content Engine via WCCP
         (Web Cache Control Protocol) has been reached.
         Subsequent WCCP requests are rejected and forwarded
         to the Origin Server until the utilization falls
         below a low watermark."
    ::= 5

cceHttpReqGroup OBJECT IDENTIFIER ::= { ciscoContentEngineMIBGroups 1 }
-- OBJECT-GROUP
--  Status
--    mandatory
--  Descr
--    HTTP proxy request group with low capacity
--     Counter32 objects.
--  objects
--    cceHttpRequestsTotal, cceHttpRequestsNoCacheTotal, 
--    cceHttpRequestsClientErrorTotal, 
--    cceHttpRequestsServerErrorTotal, cceHttpRequestsBlocked, 
--    cceHttpRequestsHits, cceHttpRequestsMisses, 
--    cceHttpRequestsBytesServedHits, 
--    cceHttpRequestsBytesServedMisses, 
--    cceHttpRequestsImsInmTotalCache, 
--    cceHttpRequestsImsInmTotalReval, cceHttpRequestsBytesClientIn, 
--    cceHttpRequestsBytesClientOut, cceHttpRequestsBytesServerIn, 
--    cceHttpRequestsBytesServerOut

cceHttpHCReqGroup OBJECT IDENTIFIER ::= { ciscoContentEngineMIBGroups 2 }
-- OBJECT-GROUP
--  Status
--    mandatory
--  Descr
--    HTTP proxy request group with high capacity
--     Counter objects.
--  objects
--    cceHttpHCRequestsTotal, cceHttpHCRequestsNoCacheTotal, 
--    cceHttpHCRequestsClientErrorTotal, 
--    cceHttpHCRequestsServerErrorTotal, cceHttpHCRequestsBlocked, 
--    cceHttpHCRequestsHits, cceHttpHCRequestsMisses, 
--    cceHttpHCRequestsBytesServedHits, 
--    cceHttpHCRequestsBytesServedMisses, 
--    cceHttpHCRequestsImsInmTotalCache, 
--    cceHttpHCRequestsImsInmTotalReval, 
--    cceHttpHCRequestsBytesClientIn, 
--    cceHttpHCRequestsBytesClientOut, 
--    cceHttpHCRequestsBytesServerIn, 
--    cceHttpHCRequestsBytesServerOut

cceHttpPerfGroup OBJECT IDENTIFIER ::= { ciscoContentEngineMIBGroups 3 }
-- OBJECT-GROUP
--  Status
--    mandatory
--  Descr
--    HTTP proxy performance group.
--  objects
--    cceHttpPerfSamplingTime, cceHttpPerfReqPerSec, 
--    cceHttpPerfBytesPerSec, cceHttpPerfServiceTime, 
--    cceHttpPerfHitServiceTime, cceHttpPerfMissServiceTime, 
--    cceHttpPerfObjectSize, cceHttpPerfCpuLoad

cceWmtReqGroup OBJECT IDENTIFIER ::= { ciscoContentEngineMIBGroups 5 }
-- OBJECT-GROUP
--  Status
--    mandatory
--  Descr
--    A collection of objects providing request statistics 
--     of WMT proxy and server.
--  objects
--    cceWmtTotalRequests, cceWmtTotalClientErrors, 
--    cceWmtTotalServerErrors, cceWmtBlockedRequests, 
--    cceWmtRequestHits, cceWmtRequestMisses, 
--    cceWmtRequestHitsBytesServed, cceWmtRequestMissesBytesServed, 
--    cceWmtTotalLiveRequests, cceWmtLiveRequestBytes, 
--    cceWmtTotalMmsuRequests, cceWmtTotalMmsuBytes, 
--    cceWmtTotalMmstRequests, cceWmtTotalMmstBytes, 
--    cceWmtTotalHttpRequests, cceWmtTotalHttpBytes, 
--    cceWmtTotalMulticastBytes

cceWmtHCGroup OBJECT IDENTIFIER ::= { ciscoContentEngineMIBGroups 6 }
-- OBJECT-GROUP
--  Status
--    mandatory
--  Descr
--    A collection of 64-bit WMT counters
--  objects
--    cceWmtHCRequestHitsBytesServed, 
--    cceWmtHCRequestMissesBytesServed, cceWmtHCLiveRequestBytes, 
--    cceWmtHCTotalMmsuBytes, cceWmtHCTotalMmstBytes, 
--    cceWmtHCTotalHttpBytes, cceWmtHCTotalMulticastBytes

cceWmtPerfGroup OBJECT IDENTIFIER ::= { ciscoContentEngineMIBGroups 7 }
-- OBJECT-GROUP
--  Status
--    mandatory
--  Descr
--    A collection of object providing performance statistics
--     of WMT proxy and server.
--  objects
--    cceWmtPerfConcurrentRequests, cceWmtPerfKbitsPerSec, 
--    cceWmtPerfMulticastSessions, cceWmtPerfMulticastKbitsPerSec

cceCseReqGroup OBJECT IDENTIFIER ::= { ciscoContentEngineMIBGroups 8 }
-- OBJECT-GROUP
--  Status
--    mandatory
--  Descr
--    A collection of objects providing request statistics
--    of a Cisco Streaming Engine.
--  objects
--    cceCseTotalRequests, cceCseRequestPacketsServed, 
--    cceCseRequestBytesServed

cceCseHCGroup OBJECT IDENTIFIER ::= { ciscoContentEngineMIBGroups 9 }
-- OBJECT-GROUP
--  Status
--    mandatory
--  Descr
--    A collection of 64 bit counters.
--  objects
--    cceCseHCRequestPacketsServed, cceCseHCRequestBytesServed

cceCsePerfGroup OBJECT IDENTIFIER ::= { ciscoContentEngineMIBGroups 10 }
-- OBJECT-GROUP
--  Status
--    mandatory
--  Descr
--    A collection of objects providing 
--     performance statistics of a Cisco Streaming Engine.
--  objects
--    cceCsePerfConcurrentReqs, cceCsePerfCurrentBandwidth

cceRpReqGroup OBJECT IDENTIFIER ::= { ciscoContentEngineMIBGroups 11 }
-- OBJECT-GROUP
--  Status
--    mandatory
--  Descr
--    A collection of objects providing 
--    request statistics of a Real Proxy.
--  objects
--    cceRpTotalHits, cceRpTotalMisses, cceRpTotalVodPassThroughs, 
--    cceRpTotalLiveSplitReqs, cceRpTotalLivePassThruSplitReqs, 
--    cceRpTotalIncomingBytes, cceRpTotalOutgoingBytes

cceRpHCReqGroup OBJECT IDENTIFIER ::= { ciscoContentEngineMIBGroups 12 }
-- OBJECT-GROUP
--  Status
--    mandatory
--  Descr
--    A collection of  64-bit Real Proxy counters
--  objects
--    cceRpHCTotalHits, cceRpHCTotalMisses, 
--    cceRpHCTotalVodPassThroughs, cceRpHCTotalLiveSplitReqs, 
--    cceRpHCTotalLivePassThruSplitReqs, cceRpHCTotalIncomingBytes, 
--    cceRpHCTotalOutgoingBytes

cceNotificationGroup OBJECT IDENTIFIER ::= { ciscoContentEngineMIBGroups 4 }
-- NOTIFICATION-GROUP
--  Status
--    mandatory
--  Descr
--    the collection of notifications used for
--    monitoring errors.
--  notifications
--    ciscoContentEngineReadDiskError, 
--    ciscoContentEngineWriteDiskError, 
--    ciscoContentEngineWriteTransFailed, 
--    ciscoContentEngineDataDiskFailed, 
--    ciscoContentEngineOverloadBypass

ciscoContentEngineMIBCompliance OBJECT IDENTIFIER ::= { ciscoContentEngineMIBCompliances 1 }
-- MODULE-COMPLIANCE
--  Status
--    deprecated
--  Descr
--    The compliance statement for Cisco Systems entities which
--     implement the Content Engine applications.
--  Module
--    >>current<<
--   MandGroup
--    cceHttpReqGroup
--   MandGroup
--    cceHttpPerfGroup

ciscoContentEngineMIBComplianceRev1 OBJECT IDENTIFIER ::= { ciscoContentEngineMIBCompliances 2 }
-- MODULE-COMPLIANCE
--  Status
--    mandatory
--  Descr
--    The compliance statement for Cisco Systems entities which
--     implement the Content Engine applications.
--  Module
--    >>current<<
--   MandGroup
--    cceHttpReqGroup
--   MandGroup
--    cceHttpPerfGroup
--   MandGroup
--    cceCseReqGroup
--   MandGroup
--    cceCseHCGroup
--   MandGroup
--    cceCsePerfGroup


END
