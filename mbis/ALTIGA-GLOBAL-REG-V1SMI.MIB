-- MIB file created 03-Dec-2002 09:41:39, by
--   SMICng version 2.2.11-beta(PRO)(Solaris), January 20, 2001. Enterprise key cisco.com

ALTIGA-GLOBAL-REG DEFINITIONS ::= BEGIN

-- From file: "ALTIGA-GLOBAL-REG.my"
-- Compile options "4 7 F H N W 03 06 0B 0G 0N 0T"

IMPORTS
    enterprises
            FROM SNMPv2-SMI-v1;

altigaGlobalRegModule OBJECT IDENTIFIER ::= { alGlobalRegModule 1 }
-- MODULE-IDENTITY
--  LastUpdated
--    200207100000Z
--  OrgName
--    Cisco Systems, Inc.
--  ContactInfo
--    Cisco Systems 
--     170 W Tasman Drive 
--     San Jose, CA  95134 
--     USA 
--    
--     Tel: +1 800 553-NETS 
--     E-mail: cs-cvpn3000@cisco.com
--  Descr
--    The Altiga Networks central registration module. 
--     
--     Acronyms 
--     The following acronyms are used in this document: 
--    
--       ACE:        Access Control Encryption 
--    
--       BwMgmt:     Bandwidth Management 
--    
--       CTCP:       Cisco Transmission Control Protocol 
--    
--       DHCP:       Dynamic Host Configuration Protocol 
--    
--       DNS:        Domain Name Service 
--    
--       FTP:        File Transfer Protocol 
--    
--       FW:         Firewall 
--    
--       HTTP:       HyperText Transfer Protocol 
--    
--       ICMP:       Internet Control Message Protocol 
--    
--       IKE:        Internet Key Exchange 
--    
--       IP:         Internet Protocol 
--    
--       LBSSF:      Load Balance Secure Session Failover 
--    
--       L2TP:       Layer-2 Tunneling Protocol 
--    
--       MIB:        Management Information Base 
--    
--       NAT:        Network Address Translation 
--    
--       NTP:        Network Time Protocol 
--    
--       PPP:        Point-to-Point Protocol 
--    
--       PPTP:       Point-to-Point Tunneling Protocol 
--    
--       SEP:        Scalable Encryption Processor 
--    
--       SNMP:       Simple Network Management Protocol 
--    
--       SSH:        Secure Shell Protocol 
--    
--       SSL:        Secure Sockets Layer 
--    
--       UDP:        User Datagram Protocol 
--     
--       VPN:        Virtual Private Network 
--     
--  RevDate
--    200207100000Z
--  RevDescr
--    Updated with new header

altigaRoot      OBJECT IDENTIFIER ::= { enterprises 3076 }
altigaReg       OBJECT IDENTIFIER ::= { altigaRoot 1 }
altigaModules   OBJECT IDENTIFIER ::= { altigaReg 1 }
alGlobalRegModule OBJECT IDENTIFIER ::= { altigaModules 1 }
alCapModule     OBJECT IDENTIFIER ::= { altigaModules 2 }
alMibModule     OBJECT IDENTIFIER ::= { altigaModules 3 }
alComplModule   OBJECT IDENTIFIER ::= { altigaModules 4 }
alVersionMibModule OBJECT IDENTIFIER ::= { altigaModules 6 }
alAccessMibModule OBJECT IDENTIFIER ::= { altigaModules 7 }
alEventMibModule OBJECT IDENTIFIER ::= { altigaModules 8 }
alAuthMibModule OBJECT IDENTIFIER ::= { altigaModules 9 }
alPptpMibModule OBJECT IDENTIFIER ::= { altigaModules 10 }
alPppMibModule  OBJECT IDENTIFIER ::= { altigaModules 11 }
alHttpMibModule OBJECT IDENTIFIER ::= { altigaModules 12 }
alIpMibModule   OBJECT IDENTIFIER ::= { altigaModules 13 }
alFilterMibModule OBJECT IDENTIFIER ::= { altigaModules 14 }
alUserMibModule OBJECT IDENTIFIER ::= { altigaModules 15 }
alTelnetMibModule OBJECT IDENTIFIER ::= { altigaModules 16 }
alFtpMibModule  OBJECT IDENTIFIER ::= { altigaModules 17 }
alTftpMibModule OBJECT IDENTIFIER ::= { altigaModules 18 }
alSnmpMibModule OBJECT IDENTIFIER ::= { altigaModules 19 }
alIpSecMibModule OBJECT IDENTIFIER ::= { altigaModules 20 }
alL2tpMibModule OBJECT IDENTIFIER ::= { altigaModules 21 }
alSessionMibModule OBJECT IDENTIFIER ::= { altigaModules 22 }
alDnsMibModule  OBJECT IDENTIFIER ::= { altigaModules 23 }
alAddressMibModule OBJECT IDENTIFIER ::= { altigaModules 24 }
alDhcpMibModule OBJECT IDENTIFIER ::= { altigaModules 25 }
alWatchdogMibModule OBJECT IDENTIFIER ::= { altigaModules 26 }
alHardwareMibModule OBJECT IDENTIFIER ::= { altigaModules 27 }
alNatMibModule  OBJECT IDENTIFIER ::= { altigaModules 28 }
alLan2LanMibModule OBJECT IDENTIFIER ::= { altigaModules 29 }
alGeneralMibModule OBJECT IDENTIFIER ::= { altigaModules 30 }
alSslMibModule  OBJECT IDENTIFIER ::= { altigaModules 31 }
alCertMibModule OBJECT IDENTIFIER ::= { altigaModules 32 }
alNtpMibModule  OBJECT IDENTIFIER ::= { altigaModules 33 }
alNetworkListMibModule OBJECT IDENTIFIER ::= { altigaModules 34 }
alSepMibModule  OBJECT IDENTIFIER ::= { altigaModules 35 }
alIkeMibModule  OBJECT IDENTIFIER ::= { altigaModules 36 }
alSyncMibModule OBJECT IDENTIFIER ::= { altigaModules 37 }
alT1E1MibModule OBJECT IDENTIFIER ::= { altigaModules 38 }
alMultiLinkMibModule OBJECT IDENTIFIER ::= { altigaModules 39 }
alSshMibModule  OBJECT IDENTIFIER ::= { altigaModules 40 }
alLBSSFMibModule OBJECT IDENTIFIER ::= { altigaModules 41 }
alDhcpServerMibModule OBJECT IDENTIFIER ::= { altigaModules 42 }
alAutoUpdateMibModule OBJECT IDENTIFIER ::= { altigaModules 43 }
alAdminAuthMibModule OBJECT IDENTIFIER ::= { altigaModules 44 }
alPPPoEMibModule OBJECT IDENTIFIER ::= { altigaModules 45 }
alXmlMibModule  OBJECT IDENTIFIER ::= { altigaModules 46 }
alCtcpMibModule OBJECT IDENTIFIER ::= { altigaModules 47 }
alFwMibModule   OBJECT IDENTIFIER ::= { altigaModules 48 }
alGroupMatchMibModule OBJECT IDENTIFIER ::= { altigaModules 49 }
alACEServerMibModule OBJECT IDENTIFIER ::= { altigaModules 50 }
alNatTMibModule OBJECT IDENTIFIER ::= { altigaModules 51 }
alBwMgmtMibModule OBJECT IDENTIFIER ::= { altigaModules 52 }
alIpSecPreFragMibModule OBJECT IDENTIFIER ::= { altigaModules 53 }
altigaGeneric   OBJECT IDENTIFIER ::= { altigaRoot 2 }
altigaProducts  OBJECT IDENTIFIER ::= { altigaRoot 3 }
altigaCaps      OBJECT IDENTIFIER ::= { altigaRoot 4 }
altigaReqs      OBJECT IDENTIFIER ::= { altigaRoot 5 }
altigaExpr      OBJECT IDENTIFIER ::= { altigaRoot 6 }
altigaHw        OBJECT IDENTIFIER ::= { altigaReg 2 }
altigaVpnHw     OBJECT IDENTIFIER ::= { altigaHw 1 }
altigaVpnChassis OBJECT IDENTIFIER ::= { altigaVpnHw 1 }
altigaVpnIntf   OBJECT IDENTIFIER ::= { altigaVpnHw 2 }
altigaVpnEncrypt OBJECT IDENTIFIER ::= { altigaVpnHw 3 }
vpnConcentrator OBJECT IDENTIFIER ::= { altigaVpnChassis 1 }
vpnRemote       OBJECT IDENTIFIER ::= { altigaVpnChassis 2 }
vpnClient       OBJECT IDENTIFIER ::= { altigaVpnChassis 3 }

vpnConcentratorRev1 OBJECT IDENTIFIER ::= { vpnConcentrator 1 }
-- OBJECT-IDENTITY
--  Status
--    mandatory
--  Descr
--    The first revision of Altiga's VPN Concentrator hardware. 
--     603e PPC processor. C10/15/20/30/50/60.

vpnConcentratorRev2 OBJECT IDENTIFIER ::= { vpnConcentrator 2 }
-- OBJECT-IDENTITY
--  Status
--    mandatory
--  Descr
--    The second revision of Altiga's VPN Concentrator hardware. 
--     740 PPC processor. C10/15/20/30/50/60.

vpnRemoteRev1 OBJECT IDENTIFIER ::= { vpnRemote 1 }
-- OBJECT-IDENTITY
--  Status
--    mandatory
--  Descr
--    The first revision of Altiga's VPN Concentrator (Remote) hardware. 
--     8240 PPC processor.

vpnClientRev1 OBJECT IDENTIFIER ::= { vpnClient 1 }
-- OBJECT-IDENTITY
--  Status
--    mandatory
--  Descr
--    The first revision of Altiga's VPN Hardware Client hardware. 
--     8260 PPC processor.


END
