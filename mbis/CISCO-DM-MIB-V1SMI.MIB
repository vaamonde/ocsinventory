-- MIB file created 28-Dec-2002 09:24:29, by
--   SMICng version 2.2.11-beta(PRO)(Solaris), January 20, 2001. Enterprise key cisco.com

CISCO-DM-MIB DEFINITIONS ::= BEGIN

-- From file: "CISCO-DM-MIB.my"
-- Compile options "4 7 F H N W 03 06 0B 0G 0N 0T"

IMPORTS
    TruthValue, RowStatus
            FROM SNMPv2-TC-v1
    ifIndex
            FROM IF-MIB
    ciscoMgmt
            FROM CISCO-SMI
    DomainId, DomainIdOrZero, FcNameId, FcNameIdOrZero
            FROM CISCO-ST-TC
    vsanIndex, notifyVsanIndex
            FROM CISCO-VSAN-MIB
    cffFcFeElementName
            FROM CISCO-FC-FE-MIB
    Counter, Gauge
            FROM RFC1155-SMI
    OBJECT-TYPE
            FROM RFC-1212
    TRAP-TYPE
            FROM RFC-1215;

ciscoDmMIB OBJECT IDENTIFIER ::= { ciscoMgmt 302 }
-- MODULE-IDENTITY
--  LastUpdated
--    200210040000Z
--  OrgName
--    Cisco Systems Inc. 
--  ContactInfo
--         Cisco Systems 
--          Customer Service 
--    Postal: 170 W Tasman Drive 
--          San Jose, CA  95134 
--          USA 
--    Tel: +1 800 553 -NETS 
--    E-mail: cs-san@cisco.com
--  Descr
--    The MIB module for the domain management functionality 
--    defined by the Fibre Channel standards (FC-SW2). For the 
--    purposes of this MIB, 'Domain Manager' is the software  
--    functionality which executes in both the principal switch 
--    and other switches.
--  RevDate
--    200210040000Z
--  RevDescr
--    Initial version of this MIB module.

ciscoDmMIBObjects OBJECT IDENTIFIER ::= { ciscoDmMIB 1 }
dmMIBConformance OBJECT IDENTIFIER ::= { ciscoDmMIB 2 }
dmConfiguration OBJECT IDENTIFIER ::= { ciscoDmMIBObjects 1 }
dmInfo          OBJECT IDENTIFIER ::= { ciscoDmMIBObjects 2 }
dmNotificationPrefix OBJECT IDENTIFIER ::= { ciscoDmMIBObjects 3 }
dmNotification  OBJECT IDENTIFIER ::= { dmNotificationPrefix 0 }
dmMIBCompliances OBJECT IDENTIFIER ::= { dmMIBConformance 1 }
dmMIBGroups     OBJECT IDENTIFIER ::= { dmMIBConformance 2 }

DomainPriority ::= Gauge(1..255)
-- TEXTUAL-CONVENTION
--  Status
--    mandatory
--  Descr
--    Priority of the switch. 
--    The principal switch selection is influenced by the 
--    priority of the switch.  
--    Some values are of importance are: 
--    1   : The highest priority in principal switch  
--          selection and is used by the user to establish 
--          which switch becomes the principal switch.  
--    255 : Indicates that the switch is not capable of 
--          acting as a principal switch.

DomainPriorityOrZero ::= INTEGER(0..255)
-- TEXTUAL-CONVENTION
--  Status
--    mandatory
--  Descr
--    This is an extension of the DomainPriority. In 
--    addition to the DomainPriority range, this also 
--    includes 0 in its range of values. The value '0' means 
--    that the priority is not known. If the meaning is 
--    different from this, then it should mentioned in the 
--    description of the object using this textual 
--    convention.

DomainInterfaceRole ::= INTEGER {
        nonPrincipal(1),
        principalUpstream(2),
        principalDownsteam(3),
        isolated(4),
        down(5),
        unknown(6)
        }
-- TEXTUAL-CONVENTION
--  Status
--    mandatory
--  Descr
--    Role of the Domain Manager interface. 
--    nonPrincipal (1)       - non-principal interface 
--    principalUpstream (2)  - upstream  principal interface 
--    principalDownsteam (3) - downstream principal interface 
--    isolated (4)           - isolated interface 
--    down (5)               - down interface 
--    unknown (6)            - unknown interface 

DmState ::= INTEGER {
        starting(1),
        unconfigured(2),
        principalSwitchSelection(3),
        domainIdDistribution(4),
        buildFabricPhase(5),
        reconfigureFabricPhase(6),
        stable(7),
        stableWithNoEports(8),
        stableWithDomainConfigured(9),
        noDomains(10),
        disabled(11),
        suspended(12),
        unknown(13)
        }
-- TEXTUAL-CONVENTION
--  Status
--    mandatory
--  Descr
--    State of the Domain Manager. 
--    starting(1)-  
--    unconfigured(2) -   
--    principalSwitchSelection(3)   - principal switch  
--                                  - selection in progress. 
--    domainIdDistribution(4)       - domain id distribution  
--                                  - in progress. 
--    buildFabricPhase(5)           - BuildFabric in  
--                                  - progress. 
--    reconfigureFabricPhase(6)     - ReconfigureFabric in  
--                                  - progress. 
--    stable(7)                     - stable. 
--    stableWithNoEports(8)         - stable with No present. 
--    stableWithDomainConfigured(9) - stable with domain  
--                                  - configured. 
--    noDomains(10)                 - no domain   
--                                  - configured/assigned. 
--    disabled(11)                  - domain manager disiabled. 
--    suspended(12)                 - corresponding VSAN is  
--                                  - suspended. 
--    unknown(13)                   - unknown. 

dmTable OBJECT-TYPE
    SYNTAX SEQUENCE OF DmEntry
    ACCESS not-accessible
    STATUS mandatory
    DESCRIPTION
        "This table contains Domain Manager related parameters  
        which can be configured and monitored. There is one  
        entry for each of the VSANs configured on this switch. 
        An entry will be created whenever a VSAN is created on 
        the switch. The entry will be removed when the  
        corresponding VSAN is deleted."
    ::= { dmConfiguration 1 }

dmEntry OBJECT-TYPE
    SYNTAX DmEntry
    ACCESS not-accessible
    STATUS mandatory
    DESCRIPTION
        "An entry provides information on the domain manager  
        for a VSAN."
    INDEX { vsanIndex }
    ::= { dmTable 1 }

DmEntry ::= SEQUENCE {
    dmConfigDomainId DomainIdOrZero,
    dmConfigDomainIdType INTEGER,
    dmEnable TruthValue,
    dmAutoReconfigure TruthValue,
    dmContiguousAllocation TruthValue,
    dmPriority DomainPriority,
    dmRestart INTEGER,
    dmFabricName FcNameIdOrZero,
    dmPrincipalSwitchWwn FcNameIdOrZero,
    dmLocalSwitchWwn FcNameIdOrZero,
    dmAssignedAreaIdList OCTET STRING,
    dmFcIdsGranted Counter,
    dmFcIdsRecovered Counter,
    dmFreeFcIds Gauge,
    dmAssignedFcIds Gauge,
    dmReservedFcIds Gauge,
    dmRunningPriority DomainPriority,
    dmPrincSwRunningPriority DomainPriority,
    dmState DmState,
    dmPrincipalSwitchSelections Counter,
    dmBuildFabrics Counter,
    dmFabricReconfigures Counter,
    dmDomainId DomainIdOrZero
    }

dmConfigDomainId OBJECT-TYPE
    SYNTAX DomainIdOrZero
--    Rsyntax INTEGER(0..239)
    ACCESS read-write
    STATUS mandatory
    DESCRIPTION
        "The configured Domain Id of the local switch on this 
        VSAN or zero if no Domain Id has been configured.  
        The meaning of this object depends on  
        dmConfigDomainIdType object. 
        
        If dmConfigDomainIdType is 'preferred', then domain Id 
        configured is called 'preferred Domain Id'. The valid 
        values are between 0 and 239. In a situation where  
        this domain could not be assigned, any other domain Id 
        would be acceptable. The value '0' means any domain Id. 
        
        If dmConfigDomainIdType is 'static', then domain Id is 
        called 'static Domain Id' and valid values are between 
        1 and 239. In a situation where this domain was  
        non-zero but could not be assigned, no other domain Id 
        would be acceptable. 
        
        If the Domain Manager is enabled on the VSAN, then a  
        RDI (Request Domain Id) will be sent requesting this  
        Domain Id. If no Domain Id can be granted in the case 
        of 'preferred' or if the configured 'static' domain Id 
        cannot be not granted then, it is an error condition.  
        When this error occurs, the E_ports on that VSAN will be 
        isolated and user will be informed via  
        'dmDomainIdNotAssigned' notification. 
        
        If the domain manager is not enabled, then the static 
        Domain Id is assumed to be granted, if it has been  
        configured (to a valid number).  
        
        If either of the domain Ids are not configured with a  
        non-zero value on this VSAN and if the domain manager is 
        not enabled, then 
        
        - switch will isolate all of its E_ports on this VSAN. 
        - The user will be informed via a notification  
          'dmDomainIdNotAssigned'."
    DEFVAL { 0 }
    ::= { dmEntry 1 }

dmConfigDomainIdType OBJECT-TYPE
    SYNTAX INTEGER {
        static(1),
        preferred(2)
        }
    ACCESS read-write
    STATUS mandatory
    DESCRIPTION
        "Type of configured Domain Id."
    DEFVAL { preferred }
    ::= { dmEntry 2 }

dmEnable OBJECT-TYPE
    SYNTAX TruthValue
--    Rsyntax INTEGER {
--        true(1),
--        false(2)
--        }
    ACCESS read-write
    STATUS mandatory
    DESCRIPTION
        "Enables the Domain Manager on this VSAN.  
        
        If enabled on an active VSAN, the switch will  
        participate in principal switch selection. 
        If disabled, the switch will participate in neither 
        the principal switch selection nor domain allocation. 
        Thus, Domain Id needs to be configured statically."
    DEFVAL { false }
    ::= { dmEntry 3 }

dmAutoReconfigure OBJECT-TYPE
    SYNTAX TruthValue
--    Rsyntax INTEGER {
--        true(1),
--        false(2)
--        }
    ACCESS read-write
    STATUS mandatory
    DESCRIPTION
        "This object determines how the switch responds to  
        certain error conditions. 
                      
        The condition that can cause these errors is  
        merging of two disjoint fabrics that have  
        overlapping Domain Id list. 
        
        If value of this object is 'true', the switch will  
        send a RCF (ReConfigureFabric) to rebuild the  
        Fabric.  
          
        If 'false' the switch will isolate the E_ports on  
        which the errors happened."
    DEFVAL { false }
    ::= { dmEntry 4 }

dmContiguousAllocation OBJECT-TYPE
    SYNTAX TruthValue
--    Rsyntax INTEGER {
--        true(1),
--        false(2)
--        }
    ACCESS read-write
    STATUS mandatory
    DESCRIPTION
        "Determines how the switch behaves when elected  
        as the principal switch. 
        If true, switch won't accept non-contiguous domain  
        IDs in RDIs and will try to replace all the Domain Ids  
        in the list with contiguous domain IDs if a RDI for a  
        contiguous Domain Id can not be fulfilled. 
        If false, then the switch acts normally in granting  
        the Domain Ids even if they are not contiguous."
    ::= { dmEntry 5 }

dmPriority OBJECT-TYPE
    SYNTAX DomainPriority
--    Rsyntax Gauge(1..255)
    ACCESS read-write
    STATUS mandatory
    DESCRIPTION
        "Priority of the switch to be used in principal switch  
        selection process."
    ::= { dmEntry 6 }

dmRestart OBJECT-TYPE
    SYNTAX INTEGER {
        nonDisruptive(1),
        disruptive(2),
        noOp(3)
        }
    ACCESS read-write
    STATUS mandatory
    DESCRIPTION
        "This object tells the Domain Manager to rebuild the  
        Domain Id tree all over again.  
          
        If this object is set to 'disruptive', then a RCF  
        (ReConfigure Fabric) is generated in the VSAN in  
        order for the fabric to recover from the errors. 
          
        If this object is set to 'nonDisruptive', then a  
        BF (Build Fabric) is generated in the VSAN.  
        
        No action is taken if this object is set to 'noOp'. 
        The value of the object when read is always 'noOp'."
    ::= { dmEntry 7 }

dmFabricName OBJECT-TYPE
    SYNTAX FcNameIdOrZero
--    Rsyntax OCTET STRING(SIZE(0|8|16))
    ACCESS read-write
    STATUS mandatory
    DESCRIPTION
        "The WWN that is used for fabric logins on this VSAN. 
        This object is used only if the value of dmEnable is  
        false. If the value of dmEnable is true, then principal 
        switch WWN is used."
    DEFVAL { '0123456789abcdef'H }
    ::= { dmEntry 8 }

dmPrincipalSwitchWwn OBJECT-TYPE
    SYNTAX FcNameIdOrZero
--    Rsyntax OCTET STRING(SIZE(0|8|16))
    ACCESS read-only
    STATUS mandatory
    DESCRIPTION
        "The WWN of the Principal Switch on this VSAN, or  
        zero-length string if the identity of the principal  
        switch is unknown."
    DEFVAL { ''H }
    ::= { dmEntry 9 }

dmLocalSwitchWwn OBJECT-TYPE
    SYNTAX FcNameIdOrZero
--    Rsyntax OCTET STRING(SIZE(0|8|16))
    ACCESS read-only
    STATUS mandatory
    DESCRIPTION
        "The WWN of the local Switch on this VSAN."
    ::= { dmEntry 10 }

dmAssignedAreaIdList OBJECT-TYPE
    SYNTAX OCTET STRING(SIZE(0..256))
    ACCESS read-only
    STATUS mandatory
    DESCRIPTION
        "The list of Area Ids which have been assigned in this  
        VSAN, formatted as an array of octets in ascending order. 
        There could zero or more Area Ids assigned on this VSAN.  
          
        Area Id is an 8-bit value. And therefore, each octet  
        represents one Area Id. So, the list containing the  
        area_IDs 23, 45, 235 and 56 would be formatted as the  
        4-octet string x'172d38eb'. 
          
        Each of these area_IDs can be used as an index to the  
        dmAreaTable to get the statistics on the area."
    ::= { dmEntry 11 }

dmFcIdsGranted OBJECT-TYPE
    SYNTAX Counter
    ACCESS read-only
    STATUS mandatory
    DESCRIPTION
        "The total number of FC IDs that are granted (for local  
        use) by the Domain Manager on the local switch since the 
        switch has been initialized. Note that all such FC IDs  
        have the local  switch's Domain Id."
    ::= { dmEntry 12 }

dmFcIdsRecovered OBJECT-TYPE
    SYNTAX Counter
    ACCESS read-only
    STATUS mandatory
    DESCRIPTION
        "The total number of FC IDs that are recovered by the  
        Domain Manager on the local switch since the switch has  
        been initialized. A recovered FC ID is one that is  
        explicitly returned after previously being granted for  
        local use."
    ::= { dmEntry 13 }

dmFreeFcIds OBJECT-TYPE
    SYNTAX Gauge
    ACCESS read-only
    STATUS mandatory
    DESCRIPTION
        "The number of FC IDs that are unassigned on this VSAN."
    ::= { dmEntry 14 }

dmAssignedFcIds OBJECT-TYPE
    SYNTAX Gauge
    ACCESS read-only
    STATUS mandatory
    DESCRIPTION
        "The number of FC IDs that are assigned on this VSAN."
    ::= { dmEntry 15 }

dmReservedFcIds OBJECT-TYPE
    SYNTAX Gauge
    ACCESS read-only
    STATUS mandatory
    DESCRIPTION
        "The number of FC IDs that are reserved on this VSAN."
    ::= { dmEntry 16 }

dmRunningPriority OBJECT-TYPE
    SYNTAX DomainPriority
--    Rsyntax Gauge(1..255)
    ACCESS read-only
    STATUS mandatory
    DESCRIPTION
        "The running priority of the local switch on this VSAN."
    ::= { dmEntry 17 }

dmPrincSwRunningPriority OBJECT-TYPE
    SYNTAX DomainPriority
--    Rsyntax Gauge(1..255)
    ACCESS read-only
    STATUS mandatory
    DESCRIPTION
        "The running priority of the principal switch on this  
        VSAN."
    ::= { dmEntry 18 }

dmState OBJECT-TYPE
    SYNTAX DmState
--    Rsyntax INTEGER {
--        starting(1),
--        unconfigured(2),
--        principalSwitchSelection(3),
--        domainIdDistribution(4),
--        buildFabricPhase(5),
--        reconfigureFabricPhase(6),
--        stable(7),
--        stableWithNoEports(8),
--        stableWithDomainConfigured(9),
--        noDomains(10),
--        disabled(11),
--        suspended(12),
--        unknown(13)
--        }
    ACCESS read-only
    STATUS mandatory
    DESCRIPTION
        "The state of the Domain Manager on the local switch on  
        this VSAN."
    ::= { dmEntry 19 }

dmPrincipalSwitchSelections OBJECT-TYPE
    SYNTAX Counter
    ACCESS read-only
    STATUS mandatory
    DESCRIPTION
        "The number of principal switch selections on this VSAN."
    ::= { dmEntry 20 }

dmBuildFabrics OBJECT-TYPE
    SYNTAX Counter
    ACCESS read-only
    STATUS mandatory
    DESCRIPTION
        "The number of 'BuildFabrics' (BFs) that have occurred  
        on this VSAN."
    ::= { dmEntry 21 }

dmFabricReconfigures OBJECT-TYPE
    SYNTAX Counter
    ACCESS read-only
    STATUS mandatory
    DESCRIPTION
        "The number of 'ReconfigureFabrics' (RCFs) that have  
        occurred on this VSAN."
    ::= { dmEntry 22 }

dmDomainId OBJECT-TYPE
    SYNTAX DomainIdOrZero
--    Rsyntax INTEGER(0..239)
    ACCESS read-only
    STATUS mandatory
    DESCRIPTION
        "The Domain Id of the local switch on this VSAN or zero  
        if no Domain Id has been assigned."
    ::= { dmEntry 23 }

dmIfTable OBJECT-TYPE
    SYNTAX SEQUENCE OF DmIfEntry
    ACCESS not-accessible
    STATUS mandatory
    DESCRIPTION
        "This table contains interface configuration of the 
        domain manager per VSAN. 
        
        An entry in this table is automatically created when  
        an E_port becomes non-isolated and there is a 
        entry in dmTable for that VSAN.  
        
        An entry is deleted automatically from this table if : 
        a) the correponding interface becomes non-existent, or 
        b) the correponding interface becomes a non-E_port 
           and all the writable objects has default values. 
                          or 
        c) the dmTable entry for the corresponding VSAN is 
           deleted. 
        
        Entries in this table can be created via dmIfRowStatus  
        only as the means to specify non-default parameter values 
        for an interface at a time when that interface is either  
        down or is a non-E_port. 
        
        So an entry in this table exists when one or both of  
        these conditions holds: 
        - one or more configuration parameters have non-default 
          values for an interface which is either down or a  
          non-E_port and corresponding VSAN has an entry in the  
          dmTable, and/or 
        - the interface is an E_port and it is up. 
        
        This has a number of consequences: 
        - an entry exists for a non-E_port or an E_port which is 
          down whenever that interface has non-default parameters 
          and the corresponding VSAN has an entry in the dmTable; 
        - an entry cannot be created (via dmIfRowStatus) for an 
          interface with default parameters; instead, the agent 
          creates/deletes an entry for an interface with default 
          parameters according to whether the E_port is up or 
          down. 
        - an entry can not be created via dmIfRowStatus unless 
          non-default parameter values are (simultaneously)  
          configured for an interface which is a non-E_port or a  
          down interface, and the correspoding VSAN has an entry 
          in the dmTable. 
        - deleting an entry via RowStatus when either the  
          interface is down and configured with non-default  
          values or the interface is up, is equivalent to  
          resetting its parameters to their default values. 
          If the interface is down and was configured with  
          default- values, then the entry would be deleted."
    ::= { dmConfiguration 2 }

dmIfEntry OBJECT-TYPE
    SYNTAX DmIfEntry
    ACCESS not-accessible
    STATUS mandatory
    DESCRIPTION
        "An entry gives information on interface  
        configuration on a particular VSAN."
    INDEX { vsanIndex, ifIndex }
    ::= { dmIfTable 1 }

DmIfEntry ::= SEQUENCE {
    dmIfRcfReject TruthValue,
    dmIfRole DomainInterfaceRole,
    dmIfRowStatus RowStatus
    }

dmIfRcfReject OBJECT-TYPE
    SYNTAX TruthValue
--    Rsyntax INTEGER {
--        true(1),
--        false(2)
--        }
    ACCESS read-write
    STATUS mandatory
    DESCRIPTION
        "This object determines if the incoming ReConfigure 
        Fabric (RCF) messages on this interface on this vsan 
        is accepted or not. If this object is 'true', then the 
        incoming RCF is rejected. If 'false', incoming RCF 
        is accepted. 
        
        Note that this object does not apply to the outgoing  
        RCFs generated by this interface."
    DEFVAL { false }
    ::= { dmIfEntry 1 }

dmIfRole OBJECT-TYPE
    SYNTAX DomainInterfaceRole
--    Rsyntax INTEGER {
--        nonPrincipal(1),
--        principalUpstream(2),
--        principalDownsteam(3),
--        isolated(4),
--        down(5),
--        unknown(6)
--        }
    ACCESS read-only
    STATUS mandatory
    DESCRIPTION
        "The role of this interface."
    ::= { dmIfEntry 2 }

dmIfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row. 
        
        This object can be used to create an entry only if the  
        corresponding interface exists. If the interface does 
        not exists, a create will fail."
    ::= { dmIfEntry 3 }

dmAreaTable OBJECT-TYPE
    SYNTAX SEQUENCE OF DmAreaEntry
    ACCESS not-accessible
    STATUS mandatory
    DESCRIPTION
        "This table contains area statistics on this domain  
        manager per VSAN. Each octet in the dmAssignedAreaList  
        can be used to index  this table to find information on  
        each area."
    ::= { dmInfo 1 }

dmAreaEntry OBJECT-TYPE
    SYNTAX DmAreaEntry
    ACCESS not-accessible
    STATUS mandatory
    DESCRIPTION
        " An entry gives information on the Area Id and all 
         Port Ids that were assigned for within an area for  
         a particular VSAN."
    INDEX { vsanIndex, dmAreaAreaId }
    ::= { dmAreaTable 1 }

DmAreaEntry ::= SEQUENCE {
    dmAreaAreaId Gauge,
    dmAreaAssignedPortIdList OCTET STRING
    }

dmAreaAreaId OBJECT-TYPE
    SYNTAX Gauge(0..255)
    ACCESS not-accessible
    STATUS mandatory
    DESCRIPTION
        "The Area Id of this area."
    ::= { dmAreaEntry 1 }

dmAreaAssignedPortIdList OBJECT-TYPE
    SYNTAX OCTET STRING(SIZE(0..256))
    ACCESS read-only
    STATUS mandatory
    DESCRIPTION
        "The list of Port Ids which have been assigned in  
        this Area and VSAN, formatted as an array of octets  
        in ascending order. There could be zero or more Port 
        Ids assigned on this Area and VSAN.  
          
        Port Id is an 8-bit value. And therefore, each octet  
        represents one Port Id. So, the list containing the  
        Port Ids 23, 45, 235 and 56 would be formatted as the 
        4-octet string x'172d38eb'."
    ::= { dmAreaEntry 2 }

dmDatabaseTable OBJECT-TYPE
    SYNTAX SEQUENCE OF DmDatabaseEntry
    ACCESS not-accessible
    STATUS mandatory
    DESCRIPTION
        "This table contains all information known by the  
        local switch about all the domains which have been  
        assigned in each of the VSANs."
    ::= { dmInfo 2 }

dmDatabaseEntry OBJECT-TYPE
    SYNTAX DmDatabaseEntry
    ACCESS not-accessible
    STATUS mandatory
    DESCRIPTION
        "An entry (conceptual row) in the dmDatabaseTable  
        containing information about one Domain Id in one  
        VSAN."
    INDEX { vsanIndex, dmDatabaseDomainId }
    ::= { dmDatabaseTable 1 }

DmDatabaseEntry ::= SEQUENCE {
    dmDatabaseDomainId DomainId,
    dmDatabaseSwitchWwn FcNameId
    }

dmDatabaseDomainId OBJECT-TYPE
    SYNTAX DomainId
--    Rsyntax INTEGER(1..239)
    ACCESS not-accessible
    STATUS mandatory
    DESCRIPTION
        "The Domain Id for which this row contains  
        information."
    ::= { dmDatabaseEntry 1 }

dmDatabaseSwitchWwn OBJECT-TYPE
    SYNTAX FcNameId
--    Rsyntax OCTET STRING(SIZE(8))
    ACCESS read-only
    STATUS mandatory
    DESCRIPTION
        "The WWN of the switch to which the corresponding  
        value of dmDatabaseDomainId is currently assigned 
        for the particular VSAN."
    ::= { dmDatabaseEntry 2 }

dmMaxFcIdCacheSize OBJECT-TYPE
    SYNTAX Gauge(1..4294967295)
    ACCESS read-only
    STATUS mandatory
    DESCRIPTION
        "The maximum number of FC Ids that can be cached in the 
        dmFcIdCacheTable."
    ::= { dmInfo 3 }

dmFcIdCacheTable OBJECT-TYPE
    SYNTAX SEQUENCE OF DmFcIdCacheEntry
    ACCESS not-accessible
    STATUS mandatory
    DESCRIPTION
        "This table contains all the FC Ids that have recently 
        been released. So it lists all the FC Ids that have  
        valid WWN to FC Id  mappings and currently not assigned  
        to any ports. These FC Id were assigned to ports and now, 
        have been released. This cached FC Id contains only Area 
        Id and Port Id information. The FC Id cache is kept to  
        provide best effort re-assignment of same FC Ids. i.e,  
        an Nx_port would get the same FC Id when it asks for a FC 
        Id again, after releasing it."
    ::= { dmInfo 4 }

dmFcIdCacheEntry OBJECT-TYPE
    SYNTAX DmFcIdCacheEntry
    ACCESS not-accessible
    STATUS mandatory
    DESCRIPTION
        "An entry (conceptual row) in the dmFcIdCacheTable  
        containing information about one FC Id that was   
        released from a WWN, corresponding to a range of one or 
        more ports. An entry is created when a FC Id is  
        released by the last port in the range. An entry is  
        deleted either when the number of rows in this table 
        reaches 'dmMaxFcIdCacheSize' if it is the oldest entry 
        (depending on the value of the object  
        'dmFcIdCacheReleasedTime') to make room for the a new  
        entry or when the this FC Id is assinged to a port."
    INDEX { vsanIndex, dmFcIdCacheWwn }
    ::= { dmFcIdCacheTable 1 }

DmFcIdCacheEntry ::= SEQUENCE {
    dmFcIdCacheWwn FcNameId,
    dmFcIdCacheAreaIdPortId OCTET STRING,
    dmFcIdCachePortIds Gauge
    }

dmFcIdCacheWwn OBJECT-TYPE
    SYNTAX FcNameId
--    Rsyntax OCTET STRING(SIZE(8))
    ACCESS not-accessible
    STATUS mandatory
    DESCRIPTION
        "The WWN of the port associated this entry."
    ::= { dmFcIdCacheEntry 1 }

dmFcIdCacheAreaIdPortId OBJECT-TYPE
    SYNTAX OCTET STRING(SIZE(2))
    ACCESS read-only
    STATUS mandatory
    DESCRIPTION
        "The Area Id and Port Id of FC Id that was assigned  
        and has since been released by this port on this  
        VSAN.  
        Note that this object is only 2 bytes and only  
        contains the Area Id and Port Id."
    ::= { dmFcIdCacheEntry 2 }

dmFcIdCachePortIds OBJECT-TYPE
    SYNTAX Gauge(0..65535)
    ACCESS read-only
    STATUS mandatory
    DESCRIPTION
        "Number of port Ids assigned and/or released starting 
        from Port Id contained in the second byte of 
        dmFcIdCacheAreaIdPortId for the Area Id contained in  
        the first byte of object dmFcIdCacheAreaIdPortId."
    ::= { dmFcIdCacheEntry 3 }

dmReConfFabricChangeNotifyEnable OBJECT-TYPE
    SYNTAX TruthValue
--    Rsyntax INTEGER {
--        true(1),
--        false(2)
--        }
    ACCESS read-write
    STATUS mandatory
    DESCRIPTION
        "Specifies whether or not the local switch should issue a 
        dmFabricChangeNotify notification on sending or receiving 
        ReConfigureFabric (RCF) on a VSAN. 
         
        If the value of the object is 'true, then the  
        notification is generated. If the value is 'false', 
        notification is not generated."
    DEFVAL { false }
    ::= { dmConfiguration 3 }

dmDomainIdNotAssignedNotify TRAP-TYPE
-- Reverse mappable trap
    ENTERPRISE dmNotificationPrefix
    VARIABLES {
        notifyVsanIndex, cffFcFeElementName }
--  Status
--    mandatory
    DESCRIPTION
        "If a Domain Id is not configured or assigned on a  
        VSAN, then the switch may isolate E_ports on that  
        VSAN. The conditions are :  
        - If the Domain Manager is enabled on the local  
          switch and its request for a configured static  
          Domain Id is rejected or no other Domain Id is  
          assigned, then the E_ports are isolated. 
        - If the domain manager is not enabled and if a  
          static Domain Id is not configured on the VSAN,  
          then the switch will isolate all of its E_ports  
          on the VSAN. 
                     
        This notification contains the vsanIndex of the VSAN  
        on which the condition happened."
    ::= 1

dmNewPrincipalSwitchNotify TRAP-TYPE
-- Reverse mappable trap
    ENTERPRISE dmNotificationPrefix
    VARIABLES {
        notifyVsanIndex, cffFcFeElementName }
--  Status
--    mandatory
    DESCRIPTION
        "This notification indicates that the sending switch  
        has become the new Principal Switch on a VSAN. This  
        notification is sent soon after its election as the  
        new Principal Switch, i.e., upon expiration of a  
        Principal Switch selection timer which is equal to  
        twice Fabric  Stability Timeout value (F_S_TOV). 
         
        This notification contains the vsanIndex of the VSAN  
        on which the switch became the Principal Switch and  
        the WWN of the switch which became the Principal  
        Switch."
    ::= 2

dmFabricChangeNotify TRAP-TYPE
-- Reverse mappable trap
    ENTERPRISE dmNotificationPrefix
    VARIABLES {
        notifyVsanIndex }
--  Status
--    mandatory
    DESCRIPTION
        "This notification is sent whenever a switch sends or  
        receives a Build Fabric (BF) or a ReConfigure Fabric  
        (RCF) message on a VSAN. 
         
        A switch can receive or issue a BuildFabric (BF) or a  
        ReConfigureFabric (RCF) message under following  
        conditions: 
        - A new link causes two disjoint fabrics in a VSAN to  
          merge into one fabric. The sent/received message is 
          BF if the Domain Id lists on the disjoint fabric  
          does not overlap and it is RCF if they overlap. 
        - An upsteam principal ISL which connects to Principal 
          switch and other switches in a VSAN fails. BF is 
          issued to see if there is an alternative path to 
          the Principal Switch. If not paths exit, then an RCF 
          is issued. 
        - A switch asks for a different set of Domain Ids  
          than the currently assigned list, the Principal  
          switch would issue an RCF. 
           
        The notification is not sent if a  
        'dmNewPrincipalSwitchNotify' notification is sent 
        for the same transition. 
        This notification contains the vsanIndex of the VSAN  
        on which RCF was issued."
    ::= 3

dmGroup OBJECT IDENTIFIER ::= { dmMIBGroups 1 }
-- OBJECT-GROUP
--  Status
--    mandatory
--  Descr
--    A collection of objects for displaying and 
--      configuring Domain Manager membership.
--  objects
--    dmConfigDomainId, dmConfigDomainIdType, dmEnable, 
--    dmAutoReconfigure, dmContiguousAllocation, dmPriority, 
--    dmRestart, dmFabricName, dmPrincipalSwitchWwn, 
--    dmLocalSwitchWwn, dmAssignedAreaIdList, dmFcIdsGranted, 
--    dmFcIdsRecovered, dmFreeFcIds, dmAssignedFcIds, 
--    dmReservedFcIds, dmRunningPriority, dmPrincSwRunningPriority, 
--    dmState, dmPrincipalSwitchSelections, dmBuildFabrics, 
--    dmFabricReconfigures, dmDomainId, 
--    dmReConfFabricChangeNotifyEnable, dmIfRcfReject, dmIfRole, 
--    dmIfRowStatus

dmDatabaseGroup OBJECT IDENTIFIER ::= { dmMIBGroups 2 }
-- OBJECT-GROUP
--  Status
--    mandatory
--  Descr
--    A collection of objects for displaying the Domain 
--    database information.
--  objects
--    dmDatabaseSwitchWwn

dmAreaGroup OBJECT IDENTIFIER ::= { dmMIBGroups 3 }
-- OBJECT-GROUP
--  Status
--    mandatory
--  Descr
--    A collection of objects for displaying the Domain  
--    area information.
--  objects
--    dmAreaAssignedPortIdList

dmCacheGroup OBJECT IDENTIFIER ::= { dmMIBGroups 4 }
-- OBJECT-GROUP
--  Status
--    mandatory
--  Descr
--    A collection of objects for displaying the Domain  
--    area information.
--  objects
--    dmMaxFcIdCacheSize, dmFcIdCacheAreaIdPortId, 
--    dmFcIdCachePortIds

dmNotificationGroup OBJECT IDENTIFIER ::= { dmMIBGroups 5 }
-- NOTIFICATION-GROUP
--  Status
--    mandatory
--  Descr
--    A collection of notifications for status monitoring 
--    and notification.
--  notifications
--    dmDomainIdNotAssignedNotify, dmNewPrincipalSwitchNotify, 
--    dmFabricChangeNotify

dmMIBCompliance OBJECT IDENTIFIER ::= { dmMIBCompliances 1 }
-- MODULE-COMPLIANCE
--  Status
--    mandatory
--  Descr
--    The compliance statement for entities which  
--    implement the Domain Manager.
--  Module
--    >>current<<
--   MandGroup
--    dmGroup
--   MandGroup
--    dmDatabaseGroup
--   MandGroup
--    dmAreaGroup
--   MandGroup
--    dmCacheGroup
--   MandGroup
--    dmNotificationGroup
--   ObjVar
--    dmIfRowStatus


END
