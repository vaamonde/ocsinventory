GWPAGERMIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell          OBJECT IDENTIFIER   ::= { enterprises 23 }
gateways        OBJECT IDENTIFIER   ::= { novell        2 }
gwPAGER         OBJECT IDENTIFIER   ::= { gateways      43 }
gwPAGERInfo     OBJECT IDENTIFIER   ::= { gwPAGER       1 }
gwPAGERTrapInfo OBJECT IDENTIFIER   ::= { gwPAGER       2 }


-- ====================================== GWPAGER Get/Set Variables =========
gwPAGERGatewayName OBJECT-TYPE
       SYNTAX  DisplayString (SIZE (0..255))
       ACCESS  read-only
       STATUS  mandatory
       DESCRIPTION
       "The GroupWise PAGER Gateway name."
   ::= { gwPAGERInfo 1 }
 
gwPAGERUptime OBJECT-TYPE
       SYNTAX  TimeTicks
       ACCESS  read-only
       STATUS  mandatory
       DESCRIPTION
      "Uptime of the GroupWise PAGER Gateway."
   ::= { gwPAGERInfo 2 }

gwPAGERGroupWiseLink OBJECT-TYPE
       SYNTAX  DisplayString (SIZE (0..5))
       ACCESS  read-only
       STATUS  mandatory
       DESCRIPTION
      "GroupWise PAGER Gateway Link: UP or DOWN"
   ::= { gwPAGERInfo 3 }

gwPAGERFrgnLink OBJECT-TYPE
       SYNTAX  DisplayString (SIZE (0..5))
       ACCESS  read-only
       STATUS  mandatory
       DESCRIPTION
      "GroupWise PAGER Gateway Foreign Link: UP or DOWN"
   ::= { gwPAGERInfo 4 }

gwPAGEROutBytes OBJECT-TYPE
       SYNTAX  Counter
       ACCESS  read-only
       STATUS  mandatory
       DESCRIPTION
      "The number of message bytes sent to GroupWise PAGER."
   ::= { gwPAGERInfo 5 }
 
gwPAGERInBytes OBJECT-TYPE
       SYNTAX  Counter
       ACCESS  read-only
       STATUS  mandatory
       DESCRIPTION
      "The number of message bytes received from GroupWise PAGER."
   ::= { gwPAGERInfo 6 }
 
gwPAGEROutMsgs OBJECT-TYPE
       SYNTAX  Counter
       ACCESS  read-only
       STATUS  mandatory
       DESCRIPTION
      "The number of messages sent to GroupWise PAGER."
   ::= { gwPAGERInfo 7 }
 
gwPAGERInMsgs OBJECT-TYPE
       SYNTAX  Counter
       ACCESS  read-only
       STATUS  mandatory
       DESCRIPTION
      "The number of messages received from PAGER."
   ::= { gwPAGERInfo 8 }
 
gwPAGEROutStatuses OBJECT-TYPE
       SYNTAX  Counter
       ACCESS  read-only
       STATUS  mandatory
       DESCRIPTION
      "The number of statuses sent to PAGER."
   ::= { gwPAGERInfo 9 }
 
gwPAGERInStatuses OBJECT-TYPE
       SYNTAX  Counter
       ACCESS  read-only
       STATUS  mandatory
       DESCRIPTION
      "The number of statuses received from PAGER."
   ::= { gwPAGERInfo 10 }
 
gwPAGEROutErrors OBJECT-TYPE
       SYNTAX  Counter
       ACCESS  read-only
       STATUS  mandatory
       DESCRIPTION
      "The number of failed transfers to PAGER."
   ::= { gwPAGERInfo 11 }
 
gwPAGERInErrors OBJECT-TYPE
       SYNTAX  Counter
       ACCESS  read-only
       STATUS  mandatory
       DESCRIPTION
      "The number of failed transfers from PAGER."
   ::= { gwPAGERInfo 12 }

-- ================================================== gwPAGERTrapInfo ========
-- The gwPAGERTrapInfo group
-- These objects are used only in traps produced by gwPAGER
 
gwPAGERTrapTime OBJECT-TYPE
		SYNTAX  INTEGER
		ACCESS  not-accessible
		STATUS  mandatory
		DESCRIPTION "The time the trap occurred. Seconds since Jan 1, 1970 (GMT)"
	::= { gwPAGERTrapInfo 1 }

-- ================================================== gwPAGER Traps =========
gwPAGERStartTrap TRAP-TYPE
		ENTERPRISE    gwPAGERInfo
		VARIABLES     {gwPAGERTrapTime, gwPAGERGatewayName}
		DESCRIPTION   "GroupWise PAGER Gateway start."
		--NMS Trap annotation
		--#TYPE       "GroupWise PAGER Gateway start."
		--#SUMMARY    "GroupWise PAGER Gateway %s has started."
		--#ARGUMENTS  {1}
		--#SEVERITY   INFORMATIONAL
		--#TIMEINDEX  0
		--#HELP       "gwALARM.HLP"
		--#HELPTAG    101		
		--#STATE      OPERATIONAL
		::= 1

gwPAGERStopTrap TRAP-TYPE
		ENTERPRISE    gwPAGERInfo
		VARIABLES     {gwPAGERTrapTime, gwPAGERGatewayName}
		DESCRIPTION   "GroupWise PAGER Gateway stop."
		--NMS Trap annotation
		--#TYPE       "GroupWise PAGER Gateway stop."
		--#SUMMARY    "GroupWise PAGER Gateway %s has stopped."
		--#ARGUMENTS  {1}
		--#SEVERITY   CRITICAL
		--#TIMEINDEX  0
		--#HELP       "gwALARM.HLP"
		--#HELPTAG    102		
		--#STATE      NONOPERATIONAL
		::= 2

gwPAGERRestartTrap TRAP-TYPE
		ENTERPRISE    gwPAGERInfo
		VARIABLES     {gwPAGERTrapTime, gwPAGERGatewayName}
		DESCRIPTION   "GroupWise PAGER Gateway restart."
		--NMS Trap annotation
		--#TYPE       "GroupWise PAGER Gateway restart."
		--#SUMMARY    "GroupWise PAGER Gateway %s has been restarted."
		--#ARGUMENTS  {1}
		--#SEVERITY   INFORMATIONAL
		--#TIMEINDEX  0
		--#HELP       "gwALARM.HLP"
		--#HELPTAG    503		
		--#STATE      OPERATIONAL
		::= 3
 
gwPAGERGroupWiseLinkTrap TRAP-TYPE
		ENTERPRISE    gwPAGERInfo
		VARIABLES     {gwPAGERTrapTime, gwPAGERGatewayName}
		DESCRIPTION   "GroupWise Link lost by GroupWise PAGER Gateway"
		--NMS Trap annotation
		--#TYPE       "GroupWise Link lost by GroupWise PAGER Gateway"
		--#SUMMARY    "GroupWise PAGER Gateway %s has lost its GroupWise Link"
		--#ARGUMENTS  {1}
		--#SEVERITY   INFORMATIONAL
		--#TIMEINDEX  0
		--#HELP       "gwALARM.HLP"
		--#HELPTAG    504		
		--#STATE      OPERATIONAL
		::= 4

gwPAGERFgnLinkTrap TRAP-TYPE
		ENTERPRISE    gwPAGERInfo
		VARIABLES     {gwPAGERTrapTime, gwPAGERGatewayName}
		DESCRIPTION   "PAGER Link lost by GroupWise PAGER Gateway"
		--NMS Trap annotation
		--#TYPE       "PAGER Link lost by GroupWise PAGER Gateway"
		--#SUMMARY    "GroupWise PAGER Gateway %s has lost its PAGER Link"
		--#ARGUMENTS  {1}
		--#SEVERITY   INFORMATIONAL
		--#TIMEINDEX  0
		--#HELP       "gwALARM.HLP"
		--#HELPTAG    505		
		--#STATE      OPERATIONAL
		::= 5


END
