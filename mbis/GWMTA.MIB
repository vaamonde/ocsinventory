-- GWMTA MIB
-- Novell GroupWise Message Transfer Agent (MTA) Management Information Base (MIB)
-- Copyright (C) 1994, 1995, 1996 Novell Inc.,  All Rights Reserved
-- Naming Tree: 1.3.6.1.4.1.23
--      iso(1) org(3) dod(6) internet(1) private(4) enterprises(1) novell (23)
-- Date: Jan 15, 1997
-- added OS and Version variables

GWMTA-MIB DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

novell         OBJECT IDENTIFIER   ::= { enterprises 23 }
mibDoc         OBJECT IDENTIFIER   ::= { novell       2 }
gwmta         OBJECT IDENTIFIER   ::= { mibDoc      37 }
mta            OBJECT IDENTIFIER   ::= { gwmta       1 }
mtaTrapInfo    OBJECT IDENTIFIER   ::= { gwmta       2 }
mtaTraps       OBJECT IDENTIFIER   ::= { gwmta       3 }

-- ====================================== MTA Get/Set Variables =========
mtaTable OBJECT-TYPE
	SYNTAX SEQUENCE OF MTAEntry
	ACCESS not-accessible
	STATUS mandatory
	DESCRIPTION "A table of MTA objects"
	::= { mta 1 }

mtaEntry OBJECT-TYPE
	SYNTAX MTAEntry
	ACCESS not-accessible
	STATUS mandatory
	DESCRIPTION "An entry in the MTA Table"
	INDEX  { mtaIndex }
	::= { mtaTable 1 }
	
MTAEntry ::=
	SEQUENCE {
			mtaIndex INTEGER,
			mtaDomainName DisplayString,
			mtaTotalDomains Gauge,
			mtaClosedDomains Gauge,
			mtaTotalPostOffices Gauge,
			mtaClosedPostOffices Gauge,
			mtaTotalGateways Gauge,
			mtaClosedGateways Gauge,
			mtaRoutedMsgs Counter,
			mtaTenMinuteRoutedMsgs Gauge,
			mtaUndeliverableMsgs Counter,
			mtaTenMinuteUndeliverableMsgs Gauge,
			mtaErrorMsgs Counter,
			mtaTenMinuteErrorMsgs Gauge,
			mtaResiliencyState INTEGER,
			mtaUptime TimeTicks,
			mtaLogLevel INTEGER,
			mtaFileLogging INTEGER,
			mtaMaxLogFileAge INTEGER,
			mtaMaxLogFileSpace INTEGER,
			mtaCurrentLogFile DisplayString,
			mtaRestart INTEGER,
			mtaGUID DisplayString,
			mtaOS DisplayString,
			mtaVersion DisplayString,
			mtaAdmThreadStatus DisplayString,
			mtaAdmCompletedMsgs Counter,
			mtaAdmErrorMsgs Counter,
			mtaAdmInQueueMsgs Guage,
			mtaAdmDBStatus DisplayString,
			mtaAdmDBSortLang DisplayString,
			mtaAdmDBRecoverCnt Counter
			}

mtaIndex OBJECT-TYPE
       SYNTAX  INTEGER
       ACCESS  read-write
       STATUS  mandatory
       DESCRIPTION
       "Index into the MTA table"
   ::= { mtaEntry 1 }

mtaDomainName OBJECT-TYPE
       SYNTAX  DisplayString (SIZE (0..255))
       ACCESS  read-only
       STATUS  mandatory
       DESCRIPTION "The Domain for which this MTA operates."
   ::= { mtaEntry 2 }

mtaTotalDomains OBJECT-TYPE
       SYNTAX  Gauge
       ACCESS  read-only
       STATUS  mandatory
       DESCRIPTION
      "Number of Domains serviced by this MTA."
   ::= { mtaEntry 3 }

mtaClosedDomains OBJECT-TYPE
       SYNTAX  Gauge
       ACCESS  read-only
       STATUS  mandatory
       DESCRIPTION
      "Number of closed Domains serviced by this MTA."
   ::= { mtaEntry 4 }

mtaTotalPostOffices OBJECT-TYPE
       SYNTAX  Gauge
       ACCESS  read-only
       STATUS  mandatory
       DESCRIPTION
      "Number of Post Offices serviced by this MTA."
   ::= { mtaEntry 5 }

mtaClosedPostOffices OBJECT-TYPE
       SYNTAX  Gauge
       ACCESS  read-only
       STATUS  mandatory
       DESCRIPTION
      "Number of closed Post Offices serviced by this MTA."
   ::= { mtaEntry 6 }

mtaTotalGateways OBJECT-TYPE
       SYNTAX  Gauge
       ACCESS  read-only
       STATUS  mandatory
       DESCRIPTION
      "Number of Gateways serviced by this MTA."
   ::= { mtaEntry 7 }

mtaClosedGateways OBJECT-TYPE
       SYNTAX  Gauge
       ACCESS  read-only
       STATUS  mandatory
       DESCRIPTION
      "Number of closed Gateways serviced by this MTA."
   ::= { mtaEntry 8 }

mtaRoutedMsgs OBJECT-TYPE
       SYNTAX  Counter
       ACCESS  read-only
       STATUS  mandatory
       DESCRIPTION
      "Number of messages routed since startup by this MTA."
   ::= { mtaEntry 9 }

mtaTenMinuteRoutedMsgs OBJECT-TYPE
       SYNTAX  Gauge
       ACCESS  read-only
       STATUS  mandatory
       DESCRIPTION
      "Number of messages routed in the past 10 minutes by this MTA."
   ::= { mtaEntry 10 }

mtaUndeliverableMsgs OBJECT-TYPE
       SYNTAX  Counter
       ACCESS  read-only
       STATUS  mandatory
       DESCRIPTION
      "Number of messages undeliverable since startup by this MTA."
   ::= { mtaEntry 11 }

mtaTenMinuteUndeliverableMsgs OBJECT-TYPE
       SYNTAX  Gauge
       ACCESS  read-only
       STATUS  mandatory
       DESCRIPTION
      "Number of messages undeliverable in the past 10 minutes by this MTA."
   ::= { mtaEntry 12 }

mtaErrorMsgs OBJECT-TYPE
       SYNTAX  Counter
       ACCESS  read-only
       STATUS  mandatory
       DESCRIPTION
      "Number of messages found in error since startup by this MTA."
   ::= { mtaEntry 13 }

mtaTenMinuteErrorMsgs OBJECT-TYPE
       SYNTAX  Gauge
       ACCESS  read-only
       STATUS  mandatory
       DESCRIPTION
      "Number of messages found in error in the past 10 minutes by this MTA."
   ::= { mtaEntry 14 }

mtaResiliencyState OBJECT-TYPE
       SYNTAX  DisplayString (SIZE (0..255))
       ACCESS  read-only
       STATUS  mandatory
       DESCRIPTION
      "Resiliency State of this MTA."
   ::= { mtaEntry 15 }

mtaUptime OBJECT-TYPE
       SYNTAX  TimeTicks
       ACCESS  read-only
       STATUS  mandatory
       DESCRIPTION
      "Uptime of this MTA."
   ::= { mtaEntry 16 }

mtaLogLevel OBJECT-TYPE
       SYNTAX  INTEGER { normal(1), verbose(2) }
       ACCESS  read-write
       STATUS  mandatory
       DESCRIPTION
      "MTA Log Level: Normal, Verbose"
   ::= { mtaEntry 17 }

mtaFileLogging OBJECT-TYPE
       SYNTAX  INTEGER { no(0), yes(1) }
       ACCESS  read-write
       STATUS  mandatory
       DESCRIPTION
      "MTA Disk Logging enabled: Yes or No"
   ::= { mtaEntry 18 }

mtaMaxLogFileAge OBJECT-TYPE
       SYNTAX  INTEGER
       ACCESS  read-write
       STATUS  mandatory
       DESCRIPTION
      "Maximum age for MTA log files."
   ::= { mtaEntry 19 }

mtaMaxLogFileSpace OBJECT-TYPE
       SYNTAX  INTEGER
       ACCESS  read-write
       STATUS  mandatory
       DESCRIPTION
      "Maximum disk space for MTA log files."
   ::= { mtaEntry 20 }

mtaCurrentLogFile OBJECT-TYPE
       SYNTAX  DisplayString (SIZE (0..255))
       ACCESS  read-only
       STATUS  mandatory
       DESCRIPTION
      "MTA current log file name."
   ::= { mtaEntry 21 }

mtaRestart OBJECT-TYPE
       SYNTAX  INTEGER { no(0), yes(1) }
       ACCESS  read-write
       STATUS  mandatory
       DESCRIPTION
       "MTA Restart: Yes or No."
   ::= { mtaEntry 22 }

mtaGUID OBJECT-TYPE
       SYNTAX  DisplayString (SIZE (0..36))
       ACCESS  read-only
       STATUS  mandatory
       DESCRIPTION
      "Message Transfer Agent globally unique identifier."
   ::= { mtaEntry 23 }

mtaOS OBJECT-TYPE
       SYNTAX  DisplayString (SIZE (0..64))
       ACCESS  read-only
       STATUS  mandatory
       DESCRIPTION
       "Operating System name and version"
   ::= { mtaEntry 24 }

mtaVersion OBJECT-TYPE
       SYNTAX  DisplayString (SIZE (0..64))
       ACCESS  read-only
       STATUS  mandatory
       DESCRIPTION
       "Version and date this agent."
   ::= { mtaEntry 25 }

mtaAdmThreadStatus OBJECT-TYPE
       SYNTAX  DisplayString (SIZE (0..64))
       ACCESS  read-only
       STATUS  mandatory
       DESCRIPTION
       "Admin thread status: Running, Suspended, Unknown."
   ::= { mtaEntry 26 }

mtaAdmCompletedMsgs OBJECT-TYPE
       SYNTAX  Counter
       ACCESS  read-only
       STATUS  mandatory
       DESCRIPTION
      "Number of Admin messages processed since startup by this MTA."
   ::= { mtaEntry 27 }

mtaAdmErrorMsgs OBJECT-TYPE
       SYNTAX  Counter
       ACCESS  read-only
       STATUS  mandatory
       DESCRIPTION
      "Number of Admin message errors since startup by this MTA."
   ::= { mtaEntry 28 }

mtaAdmInQueueMsgs OBJECT-TYPE
       SYNTAX  Gauge
       ACCESS  read-only
       STATUS  mandatory
       DESCRIPTION
      "Number of Admin messages waiting to be processed."
   ::= { mtaEntry 29 }

mtaAdmDBStatus OBJECT-TYPE
       SYNTAX  DisplayString (SIZE (0..64))
       ACCESS  read-only
       STATUS  mandatory
       DESCRIPTION
       "Domain database status: Normal, DB Error, Unknown."
   ::= { mtaEntry 30 }

mtaAdmDBSortLang OBJECT-TYPE
       SYNTAX  DisplayString (SIZE (0..64))
       ACCESS  read-only
       STATUS  mandatory
       DESCRIPTION
       "Domain database sort language."
   ::= { mtaEntry 31 }

mtaAdmDBRecoverCnt OBJECT-TYPE
       SYNTAX  Counter
       ACCESS  read-only
       STATUS  mandatory
       DESCRIPTION
      "Number of DB recoveries performed since startup by this MTA."
   ::= { mtaEntry 32 }

   
-- =================================================== mtaTrapInfo =========
-- The mtaTrapInfo group
-- These objects are used only in traps produced by MTA

mtaTrapTime OBJECT-TYPE
		SYNTAX  INTEGER
		ACCESS  not-accessible
		STATUS  mandatory
		DESCRIPTION "The time the trap occurred. Seconds since Jan 1, 1970 (GMT)"
	::= { mtaTrapInfo 1 }

mtaServerName OBJECT-TYPE
      SYNTAX  DisplayString (SIZE (0..255))
		ACCESS  not-accessible
		STATUS  mandatory
		DESCRIPTION "The logical MTA name"
	::= { mtaTrapInfo 2 }

mtaTrapDomainName OBJECT-TYPE
       SYNTAX  DisplayString (SIZE (0..255))
       ACCESS  not-accessible
       STATUS  mandatory
       DESCRIPTION "The Domain for which this MTA operates."
   ::= { mtaTrapInfo 3 }

mtaFacilityName OBJECT-TYPE
       SYNTAX  DisplayString (SIZE (0..255))
       ACCESS  not-accessible
       STATUS  mandatory
       DESCRIPTION "A Domain/PostOffice or Gateway name."
   ::= { mtaTrapInfo 4 }

mtaFacilityLink OBJECT-TYPE
       SYNTAX  DisplayString (SIZE (0..255))
       ACCESS  not-accessible
       STATUS  mandatory
       DESCRIPTION "A Domain/PostOffice or Gateway path."
   ::= { mtaTrapInfo 5 }

mtaClosureReason OBJECT-TYPE
       SYNTAX  DisplayString (SIZE (0..255))
       ACCESS  not-accessible
       STATUS  mandatory
       DESCRIPTION "Reason for facility closure."
   ::= { mtaTrapInfo 6 }

-- ================================================== MTA Traps =========
mtaStartupTrap TRAP-TYPE
		ENTERPRISE    mtaTraps
		VARIABLES     {mtaTrapTime, mtaServerName, mtaGUID}
		DESCRIPTION   "MTA started."
		--NMS Trap annotation
		--#TYPE       "MTA started."
		--#SUMMARY    "%s started."
		--#ARGUMENTS  {1}
		--#SEVERITY   INFORMATIONAL
		--#TIMEINDEX  0
		--#HELP       "GWALARM.HLP"
		--#HELPTAG    101
		--#STATE      OPERATIONAL
		::= 1

mtaShutdownTrap TRAP-TYPE
		ENTERPRISE    mtaTraps
		VARIABLES     {mtaTrapTime, mtaServerName, mtaDomainName, mtaGUID}
		DESCRIPTION   "MTA shut down."
		--NMS Trap annotation
		--#TYPE       "MTA shut down."
		--#SUMMARY    "%s for Domain %s shut down."
		--#ARGUMENTS  {1,2}
		--#SEVERITY   CRITICAL
		--#TIMEINDEX  0
		--#HELP       "GWALARM.HLP"
		--#HELPTAG    102		
		--#STATE      NONOPERATIONAL
		::= 2

mtaRestartTrap TRAP-TYPE
		ENTERPRISE    mtaTraps
		VARIABLES     {mtaTrapTime, mtaServerName, mtaDomainName, mtaGUID}
		DESCRIPTION   "MTA restart initiated."
		--NMS Trap annotation
		--#TYPE       "MTA restart initiated."
		--#SUMMARY    "%s for Domain %s was restarted."
		--#ARGUMENTS  {1,2}
		--#SEVERITY   CRITICAL
		--#TIMEINDEX  0
		--#HELP       "GWALARM.HLP"
		--#HELPTAG    203		
		--#STATE      NONOPERATIONAL
		::= 3

mtaConfigurationLoadedTrap TRAP-TYPE
		ENTERPRISE    mtaTraps
		VARIABLES     {mtaTrapTime, mtaServerName, mtaDomainName, mtaGUID}
		DESCRIPTION   "MTA configuration loaded."
		--NMS Trap annotation
		--#TYPE       "MTA configuration loaded."
		--#SUMMARY    "%s configuration for Domain %s loaded."
		--#ARGUMENTS  {1,2}
		--#SEVERITY   INFORMATIONAL
		--#TIMEINDEX  0
		--#HELP       "GWALARM.HLP"
		--#HELPTAG    204		
		--#STATE      OPERATIONAL
		::= 4

mtaFacilityClosedTrap TRAP-TYPE
		ENTERPRISE    mtaTraps
		VARIABLES     {mtaTrapTime, 
							mtaServerName, 
							mtaDomainName, 
							mtaFacilityName, 
							mtaFacilityLink,
							mtaClosureReason,
							mtaGUID}
		DESCRIPTION   "MTA facility closed."
		--NMS Trap annotation
		--#TYPE       "MTA facility closed."
		--#SUMMARY    "%s for Domain %s. Facility %s closed. Reason: %s.  Link: %s."
		--#ARGUMENTS  {1,2,3,5,4}
		--#SEVERITY   CRITICAL
		--#TIMEINDEX  0
		--#HELP       "GWALARM.HLP"
		--#HELPTAG    205		
		--#STATE      NONOPERATIONAL
		::= 5

mtaFacilityOpenedTrap TRAP-TYPE
		ENTERPRISE    mtaTraps
		VARIABLES     {mtaTrapTime, mtaServerName, mtaDomainName, 
                     mtaFacilityName,
                     mtaGUID}
		DESCRIPTION   "MTA facility opened."
		--NMS Trap annotation
		--#TYPE       "MTA facility opened."
		--#SUMMARY    "%s for Domain %s. Facility %s opened."
		--#ARGUMENTS  {1,2,3}
		--#SEVERITY   INFORMATIONAL
		--#TIMEINDEX  0
		--#HELP       "GWALARM.HLP"
		--#HELPTAG    206		
		--#STATE      OPERATIONAL
		::= 6

mtaBackupOnlineTrap TRAP-TYPE
		ENTERPRISE    mtaTraps
		VARIABLES     {mtaTrapTime, mtaServerName, mtaDomainName, mtaGUID}
		DESCRIPTION   "Backup MTA went online."
		--NMS Trap annotation
		--#TYPE       "Backup MTA went online."
		--#SUMMARY    "%s Backup for Domain %s now ONLINE."
		--#ARGUMENTS  {1,2}
		--#SEVERITY   CRITICAL
		--#TIMEINDEX  0
		--#HELP       "GWALARM.HLP"
		--#HELPTAG    207		
		--#STATE      OPERATIONAL
		::= 7

mtaBackupStandbyTrap TRAP-TYPE
		ENTERPRISE    mtaTraps
		VARIABLES     {mtaTrapTime, mtaServerName, mtaDomainName, mtaGUID}
		DESCRIPTION   "Backup MTA went standby."
		--NMS Trap annotation
		--#TYPE       "Backup MTA went standby."
		--#SUMMARY    "%s Backup for Domain %s now STANDBY."
		--#ARGUMENTS  {1,2}
		--#SEVERITY   CRITICAL
		--#TIMEINDEX  0
		--#HELP       "GWALARM.HLP"
		--#HELPTAG    208		
		--#STATE      NONOPERATIONAL
		::= 8

END
