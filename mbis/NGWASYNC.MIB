NGWASYNC DEFINITIONS ::= BEGIN

IMPORTS
        Counter, TimeTicks, Gauge, enterprises  FROM RFC1155-SMI
        DisplayString                           FROM RFC1213-MIB
        TRAP-TYPE                               FROM RFC-1215
        OBJECT-TYPE                             FROM RFC-1212;

wpcorp           OBJECT IDENTIFIER   ::= { enterprises 922 }
gateways         OBJECT IDENTIFIER   ::= { wpcorp        2 }
ngwasync         OBJECT IDENTIFIER   ::= { gateways      1 }
ngwasyncInfo     OBJECT IDENTIFIER   ::= { ngwasync      1 }
ngwasyncTrapInfo OBJECT IDENTIFIER   ::= { ngwasync      2 }


-- ====================================== NGWASYNC Get/Set Variables =========
ngwasyncGatewayName OBJECT-TYPE
       SYNTAX  DisplayString (SIZE (0..255))
       ACCESS  read-only
       STATUS  mandatory
       DESCRIPTION
       "The GroupWise Async Gateway name."
   ::= { ngwasyncInfo 1 }
 
ngwasyncUptime OBJECT-TYPE
       SYNTAX  TimeTicks
       ACCESS  read-only
       STATUS  mandatory
       DESCRIPTION
      "Uptime of the GroupWise Async Gateway."
   ::= { ngwasyncInfo 2 }

ngwasyncGroupWiseLink OBJECT-TYPE
       SYNTAX  DisplayString (SIZE (0..5))
       ACCESS  read-only
       STATUS  mandatory
       DESCRIPTION
      "GroupWise Async Gateway Link: UP or DOWN"
   ::= { ngwasyncInfo 3 }

ngwasyncFrgnLink OBJECT-TYPE
       SYNTAX  DisplayString (SIZE (0..5))
       ACCESS  read-only
       STATUS  mandatory
       DESCRIPTION
      "GroupWise Async Gateway Foreign Link: UP or DOWN"
   ::= { ngwasyncInfo 4 }

ngwasyncOutBytes OBJECT-TYPE
       SYNTAX  Counter
       ACCESS  read-only
       STATUS  mandatory
       DESCRIPTION
      "The number of message bytes sent to GroupWise Async."
   ::= { ngwasyncInfo 5 }
 
ngwasyncInBytes OBJECT-TYPE
       SYNTAX  Counter
       ACCESS  read-only
       STATUS  mandatory
       DESCRIPTION
      "The number of message bytes received from GroupWise Async."
   ::= { ngwasyncInfo 6 }
 
ngwasyncOutMsgs OBJECT-TYPE
       SYNTAX  Counter
       ACCESS  read-only
       STATUS  mandatory
       DESCRIPTION
      "The number of messages sent to GroupWise Async."
   ::= { ngwasyncInfo 7 }
 
ngwasyncInMsgs OBJECT-TYPE
       SYNTAX  Counter
       ACCESS  read-only
       STATUS  mandatory
       DESCRIPTION
      "The number of messages received from Async."
   ::= { ngwasyncInfo 8 }
 
ngwasyncOutStatuses OBJECT-TYPE
       SYNTAX  Counter
       ACCESS  read-only
       STATUS  mandatory
       DESCRIPTION
      "The number of statuses sent to Async."
   ::= { ngwasyncInfo 9 }
 
ngwasyncInStatuses OBJECT-TYPE
       SYNTAX  Counter
       ACCESS  read-only
       STATUS  mandatory
       DESCRIPTION
      "The number of statuses received from Async."
   ::= { ngwasyncInfo 10 }
 
ngwasyncOutErrors OBJECT-TYPE
       SYNTAX  Counter
       ACCESS  read-only
       STATUS  mandatory
       DESCRIPTION
      "The number of failed transfers to Async."
   ::= { ngwasyncInfo 11 }
 
ngwasyncInErrors OBJECT-TYPE
       SYNTAX  Counter
       ACCESS  read-only
       STATUS  mandatory
       DESCRIPTION
      "The number of failed transfers from Async."
   ::= { ngwasyncInfo 12 }
 

-- ================================================== ngwasyncTrapInfo ========
-- The ngwasyncTrapInfo group
-- These objects are used only in traps produced by NGWASYNC
 
ngwasyncTrapTime OBJECT-TYPE
		SYNTAX  INTEGER
		ACCESS  not-accessible
		STATUS  mandatory
		DESCRIPTION "The time the trap occurred. Seconds since Jan 1, 1970 (GMT)"
	::= { ngwasyncTrapInfo 1 }
 
-- ================================================== NGWASYNC Traps =========
ngwasyncStartTrap TRAP-TYPE
		ENTERPRISE    ngwasyncInfo
		VARIABLES     {ngwasyncTrapTime, ngwasyncGatewayName}
		DESCRIPTION   "GroupWise Async Gateway start."
		--NMS Trap annotation
		--#TYPE       "GroupWise Async Gateway start."
		--#SUMMARY    "GroupWise Async Gateway %s has started."
		--#ARGUMENTS  {1}
		--#SEVERITY   INFORMATIONAL
		--#TIMEINDEX  0
		--#STATE      OPERATIONAL
		::= 1

ngwasyncStopTrap TRAP-TYPE
		ENTERPRISE    ngwasyncInfo
		VARIABLES     {ngwasyncTrapTime, ngwasyncGatewayName}
		DESCRIPTION   "GroupWise Async Gateway stop."
		--NMS Trap annotation
		--#TYPE       "GroupWise Async Gateway stop."
		--#SUMMARY    "GroupWise Async Gateway %s has stopped."
		--#ARGUMENTS  {1}
		--#SEVERITY   CRITICAL
		--#TIMEINDEX  0
		--#STATE      NONOPERATIONAL
		::= 2

ngwasyncRestartTrap TRAP-TYPE
		ENTERPRISE    ngwasyncInfo
		VARIABLES     {ngwasyncTrapTime, ngwasyncGatewayName}
		DESCRIPTION   "GroupWise Async Gateway restart."
		--NMS Trap annotation
		--#TYPE       "GroupWise Async Gateway restart."
		--#SUMMARY    "GroupWise Async Gateway %s has been restarted."
		--#ARGUMENTS  {1}
		--#SEVERITY   INFORMATIONAL
		--#TIMEINDEX  0
		--#STATE      OPERATIONAL
		::= 3
 
ngwasyncGroupWiseLinkTrap TRAP-TYPE
		ENTERPRISE    ngwasyncInfo
		VARIABLES     {ngwasyncTrapTime, ngwasyncGatewayName}
		DESCRIPTION   "GroupWise Link lost by GroupWise Async Gateway"
		--NMS Trap annotation
		--#TYPE       "GroupWise Link lost by GroupWise Async Gateway"
		--#SUMMARY    "GroupWise Async Gateway %s has lost its GroupWise Link"
		--#ARGUMENTS  {1}
		--#SEVERITY   INFORMATIONAL
		--#TIMEINDEX  0
		--#STATE      OPERATIONAL
		::= 4


END
