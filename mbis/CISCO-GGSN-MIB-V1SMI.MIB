-- MIB file created 31-Dec-2002 12:25:52, by
--   SMICng version 2.2.11-beta(PRO)(Solaris), January 20, 2001. Enterprise key cisco.com

CISCO-GGSN-MIB DEFINITIONS ::= BEGIN

-- From file: "CISCO-GGSN-MIB.my"
-- Compile options "4 7 F H N W 03 06 0B 0G 0N 0T"

IMPORTS
    CiscoAlarmSeverity, CiscoInetAddressMask
            FROM CISCO-TC
    InterfaceIndexOrZero
            FROM IF-MIB
    DisplayString, TruthValue, TimeStamp, RowStatus
            FROM SNMPv2-TC-v1
    InetAddressType, InetAddress
            FROM INET-ADDRESS-MIB
    ciscoMgmt
            FROM CISCO-SMI
    Counter, Gauge
            FROM RFC1155-SMI
    OBJECT-TYPE
            FROM RFC-1212
    TRAP-TYPE
            FROM RFC-1215;

cGgsnMIB OBJECT IDENTIFIER ::= { ciscoMgmt 240 }
-- MODULE-IDENTITY
--  LastUpdated
--    200211210300Z
--  OrgName
--    Cisco Systems, Inc.
--  ContactInfo
--           Cisco Systems
--            Customer Service
--    
--    Postal: 170 W Tasman Drive
--            San Jose, CA  95134
--            USA
--    
--       Tel: +1 800 553-NETS
--    
--    E-mail: cs-gprs@cisco.com
--  Descr
--    This MIB module manages the Gateway GPRS Support
--    Node (GGSN) devices. 
--    
--    A GGSN device provides interworking with external 
--    packet-data network of a particular GPRS service
--    provider. It provides a combination of IP routing
--    and GPRS specific functionality to support mobile
--    users.
--    
--    GTP version1 is introduced in  UMTS release 99 and
--    Cisco GGSN will support both GTP version 1 (GTP v1)
--    and version zero (GTP v0) simultaneously. 
--    
--    GTP v1 supports multiple PDP contexts sharing one 
--    IP address.  TFTs are introduced to achieve this.
--    Each TFT is associated with a PDP context and there
--    may exist one PDP context without TFT amongst all 
--    PDP contexts sharing the same IP address. Each TFT 
--    has one to eight packet filters each assigned with
--    a precedence index.  These packet filters are 
--    evaluated one at a time against the packet header 
--    information in sequence of their precedence index.
--    A match is claimed if all the filters are matched
--    and the PDP context that the TFT belongs to will be
--    selected, else the checks are performed against the 
--    filters of another PDP context.  If the packet 
--    header doesn't contain any TFT packet filter
--    information, then the PDP context without the TFT is 
--    selected for further processing.
--    
--    Note on notifications:
--    
--    When an alarm occurs on the device, if the alarm's
--    severity is higher than the severity filter threshold,
--    a notification is generated by the device; and if
--    cGgsnNotifEnabled is 'true', then the device's
--    SNMP-engine configuration will be searched to
--    determine where to send the notification. 
--    
--    Acronyms and terms:
--    
--     APN    Access Point Name
--     ETSI   European Telecommunications Standards Institute
--     GGSN   Gateway GPRS Support Node
--     GPRS   General Packet Radio Service
--     GSM    Global System for Mobile communication
--     GTP    GPRS Tunneling Protocol
--     G-PDU  GTP PDU 
--     MS     Mobile Station
--     PDP    Packet Data Protocol
--     PDU    Protocol Data Unit
--     PLMN   Public Land Mobile Network
--     SGSN   Serving GPRS support Node
--     TFT    Traffic Flow Template
--     T-PDU  the payload of G-PDU 
--     UMTS   Universal Mobile Telecommunications System
--    
--    REFERENCE
--    
--    [1] GSM 03.60: Digital cellular telecommunications
--        system (Phase 2+); General Packet Radio Service
--        (GPRS); Service description; Stage 2. V7.1.0
--    
--    [2] GSM 09.60: Digital cellular telecommunication
--        system (Phase 2+); General Packet Radio Service
--        (GPRS); GPRS Tunnelling Protocol (GTP) across
--        Gn and Gp Interface. V7.3.0
--    
--    [3] 3GPP; Technical Specification Group Services
--        and System Aspects; QoS Concept and Architecture.
--        3G TS 23.107 v3.2.0.
--    
--    [4] 3GPP; Technical Specification Group Core Network;
--        General Packet Radio Service(GPRS); GPRS 
--        Tunnelling Protocol (GTP) across Gn and Gp 
--        Interface (Release 1999). 3G TS 29.060 v3.5.0.
--  RevDate
--    200211210300Z
--  RevDescr
--    + Added cGgsnPlmnIpAddrRangeTable to 
--       cGgsnConfigurations.
--     + Added cGgsnTftSemanticErrorPdps, 
--       cGgsnTftSyntacticErrorPdps,
--       cGgsnPktFilterSemanticErrorPdps,
--       cGgsnPktFilterSyntacticErrorPdps to cGgsnStatistics.
--     + Added cGgsnActiveGtpVersion0Pdps,
--       cGgsnActiveGtpVersion1Pdps, cGgsnGtpEncapInterface
--       to cGgsnStatus.
--  RevDate
--    200112081500Z
--  RevDescr
--    Initial version of this MIB module.

cGgsnMIBObjects OBJECT IDENTIFIER ::= { cGgsnMIB 1 }
cGgsnStatistics OBJECT IDENTIFIER ::= { cGgsnMIBObjects 1 }
cGgsnNotifMgmt  OBJECT IDENTIFIER ::= { cGgsnMIBObjects 2 }
cGgsnConfigurations OBJECT IDENTIFIER ::= { cGgsnMIBObjects 3 }
cGgsnStatus     OBJECT IDENTIFIER ::= { cGgsnMIBObjects 4 }
cGgsnNotifPrefix OBJECT IDENTIFIER ::= { cGgsnMIB 2 }
cGgsnNotifications OBJECT IDENTIFIER ::= { cGgsnNotifPrefix 0 }
cGgsnMIBConformances OBJECT IDENTIFIER ::= { cGgsnMIB 3 }
cGgsnMIBCompliances OBJECT IDENTIFIER ::= { cGgsnMIBConformances 1 }
cGgsnMIBGroups  OBJECT IDENTIFIER ::= { cGgsnMIBConformances 2 }

cGgsnSentSigMessages OBJECT-TYPE
    SYNTAX Counter
--  Units
--    packets
    ACCESS read-only
    STATUS mandatory
    DESCRIPTION
        "The number of GTP signalling messages sent."
    ::= { cGgsnStatistics 1 }

cGgsnReceivedSigMessages OBJECT-TYPE
    SYNTAX Counter
--  Units
--    packets
    ACCESS read-only
    STATUS mandatory
    DESCRIPTION
        "The number of GTP signalling messages received."
    ::= { cGgsnStatistics 2 }

cGgsnUnexpectedSigMessages OBJECT-TYPE
    SYNTAX Counter
--  Units
--    packets
    ACCESS read-only
    STATUS mandatory
    DESCRIPTION
        "The number of unexpected GTP signalling messages received."
    ::= { cGgsnStatistics 3 }

cGgsnSentGPDUs OBJECT-TYPE
    SYNTAX Counter
--  Units
--    packets
    ACCESS read-only
    STATUS mandatory
    DESCRIPTION
        "The number of G-PDU messages sent."
    ::= { cGgsnStatistics 4 }

cGgsnReceivedGPDUs OBJECT-TYPE
    SYNTAX Counter
--  Units
--    packets
    ACCESS read-only
    STATUS mandatory
    DESCRIPTION
        "The number of G-PDU messages received."
    ::= { cGgsnStatistics 5 }

cGgsnSentGPDUOctets OBJECT-TYPE
    SYNTAX Counter
--  Units
--    bytes
    ACCESS read-only
    STATUS mandatory
    DESCRIPTION
        "The number of total bytes sent in G-PDU messages."
    ::= { cGgsnStatistics 6 }

cGgsnReceivedGPDUOctets OBJECT-TYPE
    SYNTAX Counter
--  Units
--    bytes
    ACCESS read-only
    STATUS mandatory
    DESCRIPTION
        "The number of total bytes received in G-PDU messages."
    ::= { cGgsnStatistics 7 }

cGgsnUnexpectedGPDUs OBJECT-TYPE
    SYNTAX Counter
--  Units
--    packets
    ACCESS read-only
    STATUS mandatory
    DESCRIPTION
        "The number of unexpected G-PDU messages, for example,
        non existent PDP contexts and ACL denial."
    ::= { cGgsnStatistics 8 }

cGgsnActivationRejectedPdps OBJECT-TYPE
    SYNTAX Counter
--  Units
--    packets
    ACCESS read-only
    STATUS mandatory
    DESCRIPTION
        "The number of PDP contexts that the activation request
        was rejected."
    ::= { cGgsnStatistics 9 }

cGgsnOutOfResourcePdps OBJECT-TYPE
    SYNTAX Counter
--  Units
--    packets
    ACCESS read-only
    STATUS mandatory
    DESCRIPTION
        "The number of PDP contexts that the activation request
        rejected due to the GGSN running out of resources for
        transmitting GTP packets. Examples:
         - Out of memory;
         - The number of PDPs on GGSN reached limit;
         - all dynamic PDP address are occupied;"
    ::= { cGgsnStatistics 10 }

cGgsnParserErrorMessages OBJECT-TYPE
    SYNTAX Counter
--  Units
--    packets
    ACCESS read-only
    STATUS mandatory
    DESCRIPTION
        "The number of GTP messages received with wrong value.
        It includes the following cases:
        
         - mandatory and optional information element in the GTP
           packet is duplicated, missing, unknown, incorrect or
           out of order.
        
         - the GTP message is too short to hold the GTP header for
           the supported version.
        
         - the GTP messages running an unsupported version of GTP.
        
         - Unknown GTP message type."
    ::= { cGgsnStatistics 11 }

cGgsnTotalCreatedPdps OBJECT-TYPE
    SYNTAX Counter
--  Units
--    packets
    ACCESS read-only
    STATUS mandatory
    DESCRIPTION
        "This object represents the total number of PDP contexts 
        created."
    ::= { cGgsnStatistics 12 }

cGgsnTotalDeletedPdps OBJECT-TYPE
    SYNTAX Counter
--  Units
--    packets
    ACCESS read-only
    STATUS mandatory
    DESCRIPTION
        "This object represents the total number of PDP contexts
        deleted."
    ::= { cGgsnStatistics 13 }

cGgsnTotalNetworkInitPdps OBJECT-TYPE
    SYNTAX Counter
--  Units
--    packets
    ACCESS read-only
    STATUS mandatory
    DESCRIPTION
        "This object represents the total number of PDP contexts
        activated by the GGSN that were initiated by the PDN."
    ::= { cGgsnStatistics 14 }

cGgsnTotalPppPdpsCreated OBJECT-TYPE
    SYNTAX Counter
--  Units
--    packets
    ACCESS read-only
    STATUS mandatory
    DESCRIPTION
        "This object represents the total number of PPP PDP 
        contexts created."
    ::= { cGgsnStatistics 15 }

cGgsnTotalPppPdpsDeleted OBJECT-TYPE
    SYNTAX Counter
--  Units
--    packets
    ACCESS read-only
    STATUS mandatory
    DESCRIPTION
        "This object represents the total number of PPP PDP
        contexts deleted."
    ::= { cGgsnStatistics 16 }

cGgsnOutOfResourcePppRegenPdps OBJECT-TYPE
    SYNTAX Counter
--  Units
--    packets
    ACCESS read-only
    STATUS mandatory
    DESCRIPTION
        "This object represents the total number of create PDP 
        context and delete PDP context requests rejected due to 
        unavailable resource on the GGSN for PPP regeneration."
    ::= { cGgsnStatistics 17 }

cGgsnDroppedPppRegenPdps OBJECT-TYPE
    SYNTAX Counter
--  Units
--    packets
    ACCESS read-only
    STATUS mandatory
    DESCRIPTION
        "This object represents the total number of create PDP 
        context and delete PDP context requests that were dropped 
        due to the threshold limit being reached for maximum number
        of PPP regeneration sessions allowed on the GGSN."
    ::= { cGgsnStatistics 18 }

cGgsnTftSemanticErrorPdps OBJECT-TYPE
    SYNTAX Counter
    ACCESS read-only
    STATUS mandatory
    DESCRIPTION
        "This object represents the total number of received PDP 
        context messages that had TFTs with semantic errors."
    REFERENCE
        "3GPP; Technical Specification Group Core Network;
        General Packet Radio Service(GPRS); GPRS
        Tunnelling Protocol (GTP) across Gn and Gp
        Interface (Release 1999). 3G TS 29.060 v3.5.0."
    ::= { cGgsnStatistics 19 }

cGgsnTftSyntacticErrorPdps OBJECT-TYPE
    SYNTAX Counter
    ACCESS read-only
    STATUS mandatory
    DESCRIPTION
        "This object represents the total number of received PDP 
        context messages that had TFTs with syntactic errors."
    REFERENCE
        "3GPP; Technical Specification Group Core Network;
        General Packet Radio Service(GPRS); GPRS
        Tunnelling Protocol (GTP) across Gn and Gp
        Interface (Release 1999). 3G TS 29.060 v3.5.0."
    ::= { cGgsnStatistics 20 }

cGgsnPktFilterSemanticErrorPdps OBJECT-TYPE
    SYNTAX Counter
    ACCESS read-only
    STATUS mandatory
    DESCRIPTION
        "This object represents the total number of received PDP 
        context messages that had packet filters with semantic errors."
    REFERENCE
        "3GPP; Technical Specification Group Core Network;
        General Packet Radio Service(GPRS); GPRS
        Tunnelling Protocol (GTP) across Gn and Gp
        Interface (Release 1999). 3G TS 29.060 v3.5.0."
    ::= { cGgsnStatistics 21 }

cGgsnPktFilterSyntacticErrorPdps OBJECT-TYPE
    SYNTAX Counter
    ACCESS read-only
    STATUS mandatory
    DESCRIPTION
        "This object represents the total number of received PDP 
        context messages that had packet filters with syntactic
        errors."
    REFERENCE
        "3GPP; Technical Specification Group Core Network;
        General Packet Radio Service(GPRS); GPRS
        Tunnelling Protocol (GTP) across Gn and Gp
        Interface (Release 1999). 3G TS 29.060 v3.5.0."
    ::= { cGgsnStatistics 22 }

cGgsnNotifEnabled OBJECT-TYPE
    SYNTAX TruthValue
--    Rsyntax INTEGER {
--        true(1),
--        false(2)
--        }
    ACCESS read-write
    STATUS mandatory
    DESCRIPTION
        "Indicates whether cGgsnNotification notification will
        be sent when a notification is generated by the device.
          - 'true',  it will enable the device to send a notification,
                     as well as logging the notification to the
                     cGgsnHistNotifTable.
          - 'false', it will prevent the device from sending out a
                     notification, but it will still log the
                     notification into cGgsnHistNotifTable."
    DEFVAL { false }
    ::= { cGgsnNotifMgmt 1 }

cGgsnNotifLeastSeverLevel OBJECT-TYPE
    SYNTAX CiscoAlarmSeverity
--    Rsyntax INTEGER {
--        cleared(1),
--        indeterminate(2),
--        critical(3),
--        major(4),
--        minor(5),
--        warning(6),
--        info(7)
--        }
    ACCESS read-write
    STATUS mandatory
    DESCRIPTION
        "Indicates the least severity level of the cGgsnNotification
        notifications to be generated by the device. Thus, notifications
        are not generated for alarms with a severity level less urgent 
        than the value of this object. This object cannot be set to
        cleared(1) or indeterminate(2)."
    DEFVAL { info }
    ::= { cGgsnNotifMgmt 2 }

cGgsnGeneratedNotifs OBJECT-TYPE
    SYNTAX Counter
--  Units
--    notifications
    ACCESS read-only
    STATUS mandatory
    DESCRIPTION
        "The number of cGgsnNotification notifications that have
        been generated since sysUpTime."
    ::= { cGgsnNotifMgmt 3 }

cGgsnIgnoredAlarms OBJECT-TYPE
    SYNTAX Counter
--  Units
--    notifications
    ACCESS read-only
    STATUS mandatory
    DESCRIPTION
        "The number of alarms which are less severe than
        cGgsnNotifLeastSeverLevel since sysUpTime, and thus,
        for which no notification was generated."
    ::= { cGgsnNotifMgmt 4 }

cGgsnHistNotifMaxLength OBJECT-TYPE
    SYNTAX INTEGER(1..2147483647)
--  Units
--    entries
    ACCESS read-write
    STATUS mandatory
    DESCRIPTION
        "The maximum number of entries to be retained in the
        cGgsnHistNotifTable. When the table is full, the oldest 
        entries are removed to make space for new entries."
    DEFVAL { 100 }
    ::= { cGgsnNotifMgmt 5 }

cGgsnHistNotifLatestIndex OBJECT-TYPE
    SYNTAX Gauge(1..4294967295)
    ACCESS read-only
    STATUS mandatory
    DESCRIPTION
        "The value of cGgsnHistNotifIndex for the most recently 
         created entry in cGgsnHistNotifTable."
    ::= { cGgsnNotifMgmt 6 }

cGgsnHistNotifTable OBJECT-TYPE
    SYNTAX SEQUENCE OF CGgsnHistNotifEntry
    ACCESS not-accessible
    STATUS mandatory
    DESCRIPTION
        "A history table of the most recent cGgsnNotification
        notifications generated by this device.
        If a new cGgsnNotification notification is generated when
        the number of entries is equal to cGgsnHistNotifMaxLength,
        then the oldest entry is deleted and replaced with an entry
        for the latest notification."
    ::= { cGgsnNotifMgmt 7 }

cGgsnHistNotifEntry OBJECT-TYPE
    SYNTAX CGgsnHistNotifEntry
    ACCESS not-accessible
    STATUS mandatory
    DESCRIPTION
        "Detailed information concerning a particular notification
        that previously generated from this device."
    INDEX { cGgsnHistNotifIndex }
    ::= { cGgsnHistNotifTable 1 }

CGgsnHistNotifEntry ::= SEQUENCE {
    cGgsnHistNotifIndex Gauge,
    cGgsnHistNotifType INTEGER,
    cGgsnHistNotifSeverity CiscoAlarmSeverity,
    cGgsnHistNotifTimestamp TimeStamp,
    cGgsnHistNotifGgsnIpAddrType InetAddressType,
    cGgsnHistNotifGgsnIpAddr InetAddress,
    cGgsnHistNotifInfo DisplayString
    }

cGgsnHistNotifIndex OBJECT-TYPE
    SYNTAX Gauge(1..4294967295)
    ACCESS not-accessible
    STATUS mandatory
    DESCRIPTION
        "A monotonically increasing integer for the sole purpose of
        indexing notifications. When it reaches the maximum value,
        it wraps the value back to 1."
    ::= { cGgsnHistNotifEntry 1 }

cGgsnHistNotifType OBJECT-TYPE
    SYNTAX INTEGER {
        ggsnServiceUp(1),
        ggsnServiceDown(2),
        mapSgsnUp(3),
        mapSgsnDown(4),
        noResource(5),
        noRADIUS(6),
        noDHCPServer(7),
        ipAllocationFail(8),
        authenticationFail(9),
        apnUnreachable(10)
        }
    ACCESS read-only
    STATUS mandatory
    DESCRIPTION
        "This object indicates the type of notification."
    ::= { cGgsnHistNotifEntry 2 }

cGgsnHistNotifSeverity OBJECT-TYPE
    SYNTAX CiscoAlarmSeverity
--    Rsyntax INTEGER {
--        cleared(1),
--        indeterminate(2),
--        critical(3),
--        major(4),
--        minor(5),
--        warning(6),
--        info(7)
--        }
    ACCESS read-only
    STATUS mandatory
    DESCRIPTION
        "This object indicates the severity level of the
        notification. This object cannot be set to cleared(1)
        or indeterminate(2)."
    ::= { cGgsnHistNotifEntry 3 }

cGgsnHistNotifTimestamp OBJECT-TYPE
    SYNTAX TimeStamp
--    Rsyntax TimeTicks
    ACCESS read-only
    STATUS mandatory
    DESCRIPTION
        "This object indicates the value of sysUpTime when
        this notification was generated."
    ::= { cGgsnHistNotifEntry 4 }

cGgsnHistNotifGgsnIpAddrType OBJECT-TYPE
    SYNTAX InetAddressType
--    Rsyntax INTEGER {
--        ?? enum value of zero may cause problems
--        unknown(0),
--        ipv4(1),
--        ipv6(2),
--        dns(16)
--        }
    ACCESS read-only
    STATUS mandatory
    DESCRIPTION
        "This object indicates the type of Internet address
         by which cGgsnHistNotifGgsnIpAddr is reachable."
    ::= { cGgsnHistNotifEntry 5 }

cGgsnHistNotifGgsnIpAddr OBJECT-TYPE
    SYNTAX InetAddress
--    Rsyntax OCTET STRING(SIZE(0..255))
    ACCESS read-only
    STATUS mandatory
    DESCRIPTION
        "The object indicates the IP address that uniquely
        identifies the device which generated the notification."
    ::= { cGgsnHistNotifEntry 6 }

cGgsnHistNotifInfo OBJECT-TYPE
    SYNTAX DisplayString(SIZE(1..64))
--    Rsyntax OCTET STRING(SIZE(1..64))
    ACCESS read-only
    STATUS mandatory
    DESCRIPTION
        "A textual description of cGgsnHistNotifType, which
        potentially contains additional information (more than
        just the type of alarm).
        If the text of the message exceeds 64 bytes, the message
        will be truncated to 63 bytes and a '*' character will
        be appended to indicate the message has been truncated."
    ::= { cGgsnHistNotifEntry 7 }

cGgsnDefaultIpAllocationMethod OBJECT-TYPE
    SYNTAX INTEGER {
        disable(1),
        dhcp(2),
        radius(3)
        }
    ACCESS read-write
    STATUS mandatory
    DESCRIPTION
        "Specifies the default method by which the GGSN obtains 
         address leases for mobile user sessions.
        
            - 'disable', which indicates that dynamic address 
            allocation is disabled.
        
            - 'dhcp', which indicates that the DHCP server 
            will be used.
        
            - 'radius', which indicates that the radius server
            will be used."
    DEFVAL { disable }
    ::= { cGgsnConfigurations 1 }

cGgsnIdlePdpPurgeTimer OBJECT-TYPE
    SYNTAX Gauge(0..255)
--  Units
--    hours
    ACCESS read-write
    STATUS mandatory
    DESCRIPTION
        "This object specifies the time that the GGSN waits
         before purging idle PDP contexts. A value '0' will
         disable the purge timer."
    DEFVAL { 72 }
    ::= { cGgsnConfigurations 2 }

cGgsnIpDupProtectTable OBJECT-TYPE
    SYNTAX SEQUENCE OF CGgsnIpDupProtectEntry
    ACCESS not-accessible
    STATUS mandatory
    DESCRIPTION
        "This table contains the range of IP address used in the 
        GPRS PLMN. These IP addresses are used to avoid IP address 
        duplication in GPRS network. IP address duplication occurs 
        when a MS uses an IP address which is already used in the PLMN.
        The IP addresses configured inside GPRS network should be in 
        these ranges and MS IP address should not be in this range."
    ::= { cGgsnConfigurations 3 }

cGgsnIpDupProtectEntry OBJECT-TYPE
    SYNTAX CGgsnIpDupProtectEntry
    ACCESS not-accessible
    STATUS mandatory
    DESCRIPTION
        "Entry containing the start and end IP address in the address 
         range. An Entry with start IP > end IP is not allowed.
         No new entry will be accepted if that would cause any IP
         address(es) to be represented by more than one row in this 
         table."
    INDEX { cGgsnMsExcludeRangeStartIpType, cGgsnMsExcludeRangeStartIp, cGgsnMsExcludeRangeEndIpType, cGgsnMsExcludeRangeEndIp }
    ::= { cGgsnIpDupProtectTable 1 }

CGgsnIpDupProtectEntry ::= SEQUENCE {
    cGgsnMsExcludeRangeStartIpType InetAddressType,
    cGgsnMsExcludeRangeStartIp InetAddress,
    cGgsnMsExcludeRangeEndIpType InetAddressType,
    cGgsnMsExcludeRangeEndIp InetAddress,
    cGgsnIpDupProtectRowStatus RowStatus
    }

cGgsnMsExcludeRangeStartIpType OBJECT-TYPE
    SYNTAX InetAddressType
--    Rsyntax INTEGER {
--        ?? enum value of zero may cause problems
--        unknown(0),
--        ipv4(1),
--        ipv6(2),
--        dns(16)
--        }
    ACCESS not-accessible
    STATUS mandatory
    DESCRIPTION
        "The type of Internet address by which 
        cGgsnMsExcludeRangeStartIp is reachable. The value of this 
        object should be same as cGgsnMsExcludeRangeEndIpType.
        Only ipv4(1) addresses are supported."
    ::= { cGgsnIpDupProtectEntry 1 }

cGgsnMsExcludeRangeStartIp OBJECT-TYPE
    SYNTAX InetAddress(SIZE(4..20))
--    Rsyntax OCTET STRING(SIZE(4..20))
    ACCESS not-accessible
    STATUS mandatory
    DESCRIPTION
        "Starting IP address in the address range."
    ::= { cGgsnIpDupProtectEntry 2 }

cGgsnMsExcludeRangeEndIpType OBJECT-TYPE
    SYNTAX InetAddressType
--    Rsyntax INTEGER {
--        ?? enum value of zero may cause problems
--        unknown(0),
--        ipv4(1),
--        ipv6(2),
--        dns(16)
--        }
    ACCESS not-accessible
    STATUS mandatory
    DESCRIPTION
        "The type of Internet address by which cGgsnMsExcludeRangeEndIp
        is reachable. The value of this object should be same as
        cGgsnMsExcludeRangeStartIpType. Only ipv4(1) addresses are 
        supported."
    ::= { cGgsnIpDupProtectEntry 3 }

cGgsnMsExcludeRangeEndIp OBJECT-TYPE
    SYNTAX InetAddress(SIZE(4..20))
--    Rsyntax OCTET STRING(SIZE(4..20))
    ACCESS not-accessible
    STATUS mandatory
    DESCRIPTION
        "Ending IP address in the address range."
    ::= { cGgsnIpDupProtectEntry 4 }

cGgsnIpDupProtectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        To delete a row, set this object to 'destroy'."
    ::= { cGgsnIpDupProtectEntry 5 }

cGgsnDefaultAggregTable OBJECT-TYPE
    SYNTAX SEQUENCE OF CGgsnDefaultAggregEntry
    ACCESS not-accessible
    STATUS mandatory
    DESCRIPTION
        "This table contains the list of default aggregate routes 
        configured on the GGSN. GGSN uses a static host route to 
        forward user data packets for each PDP context received 
        from Gi interface to Gn interface. Using the aggregate 
        route (address range), the total number of static routes 
        implemented in the GGSN for PDP requests can be greatly 
        reduced."
    ::= { cGgsnConfigurations 4 }

cGgsnDefaultAggregEntry OBJECT-TYPE
    SYNTAX CGgsnDefaultAggregEntry
    ACCESS not-accessible
    STATUS mandatory
    DESCRIPTION
        "An Entry contains the IP network prefix which is used to 
        combine the routes of PDP requests for the same network as 
        a single route on the GGSN."
    INDEX { cGgsnDefaultAggregIpAddrType, cGgsnDefaultAggregIpAddr, cGgsnDefaultAggregIpMask }
    ::= { cGgsnDefaultAggregTable 1 }

CGgsnDefaultAggregEntry ::= SEQUENCE {
    cGgsnDefaultAggregIpAddrType InetAddressType,
    cGgsnDefaultAggregIpAddr InetAddress,
    cGgsnDefaultAggregIpMask CiscoInetAddressMask,
    cGgsnDefaultAggregRowStatus RowStatus
    }

cGgsnDefaultAggregIpAddrType OBJECT-TYPE
    SYNTAX InetAddressType
--    Rsyntax INTEGER {
--        ?? enum value of zero may cause problems
--        unknown(0),
--        ipv4(1),
--        ipv6(2),
--        dns(16)
--        }
    ACCESS not-accessible
    STATUS mandatory
    DESCRIPTION
        "This object specifies the type of Internet address denoted by
        cGgsnDefaultAggregIpAddr. Only ipv4(1) addresses are supported."
    ::= { cGgsnDefaultAggregEntry 1 }

cGgsnDefaultAggregIpAddr OBJECT-TYPE
    SYNTAX InetAddress(SIZE(4..20))
--    Rsyntax OCTET STRING(SIZE(4..20))
    ACCESS not-accessible
    STATUS mandatory
    DESCRIPTION
        "This object specifies the IP address whose network prefix
        is going to be defined by cGgsnDefaultAggregIpMask."
    ::= { cGgsnDefaultAggregEntry 2 }

cGgsnDefaultAggregIpMask OBJECT-TYPE
    SYNTAX CiscoInetAddressMask
--    Rsyntax Gauge(0..128)
    ACCESS not-accessible
    STATUS mandatory
    DESCRIPTION
        "This object specifies the net-mask pertaining to 
        cGgsnDefaultAggregIpAddr."
    ::= { cGgsnDefaultAggregEntry 3 }

cGgsnDefaultAggregRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        To delete a row, set this object to 'destroy'.
        The values 'createAndWait' and 'notInService' are
        not supported."
    ::= { cGgsnDefaultAggregEntry 4 }

cGgsnDefaultAaaAuthServerGroup OBJECT-TYPE
    SYNTAX DisplayString
--    Rsyntax OCTET STRING(SIZE(0..255))
    ACCESS read-write
    STATUS mandatory
    DESCRIPTION
        "This object specifies the AAA radius server group
        that is used for authentication by all APN's on this GGSN."
    ::= { cGgsnConfigurations 5 }

cGgsnDefaultAaaAccServerGroup OBJECT-TYPE
    SYNTAX DisplayString
--    Rsyntax OCTET STRING(SIZE(0..255))
    ACCESS read-write
    STATUS mandatory
    DESCRIPTION
        "This object specifies the AAA radius server group
        that is used for accounting  by all APN's on this GGSN."
    ::= { cGgsnConfigurations 6 }

cGgsnPppVirtualTemplate OBJECT-TYPE
    SYNTAX InterfaceIndexOrZero
--    Rsyntax INTEGER(0..2147483647)
    ACCESS read-write
    STATUS mandatory
    DESCRIPTION
        "This object represents the virtual template interface used
        by PPP Type PDP's."
    ::= { cGgsnConfigurations 7 }

cGgsnPppRegenVirtualTemplate OBJECT-TYPE
    SYNTAX InterfaceIndexOrZero
--    Rsyntax INTEGER(0..2147483647)
    ACCESS read-write
    STATUS mandatory
    DESCRIPTION
        "This object represents the virtual template interface used
        for PPP Regeneration by the APN's on which PPP Regeneration 
        is configured.
        
        The value zero indicates that no interface is specified."
    DEFVAL { 0 }
    ::= { cGgsnConfigurations 8 }

cGgsnPlmnIpAddrRangeTable OBJECT-TYPE
    SYNTAX SEQUENCE OF CGgsnPlmnIpAddrRangeEntry
    ACCESS not-accessible
    STATUS mandatory
    DESCRIPTION
        "This table contains the range of IP addresses that belong 
        to the PLMN nodes in a GPRS network. This range does not 
        include address of various entities like RADIUS, DHCP, DNS 
        servers, etc., which are not part of PLMN."
    ::= { cGgsnConfigurations 9 }

cGgsnPlmnIpAddrRangeEntry OBJECT-TYPE
    SYNTAX CGgsnPlmnIpAddrRangeEntry
    ACCESS not-accessible
    STATUS mandatory
    DESCRIPTION
        "Entry containing the first and last IP address in the address
         range. An Entry with first-IP > last-IP is not allowed. No 
         new entry will be accepted if that would cause any IP 
         address(es) to be represented by more than one row in this 
         table."
    INDEX { cGgsnPlmnAddrRangeIpAddrType, cGgsnPlmnAddrRangeFirstIp, cGgsnPlmnAddrRangeLastIp }
    ::= { cGgsnPlmnIpAddrRangeTable 1 }

CGgsnPlmnIpAddrRangeEntry ::= SEQUENCE {
    cGgsnPlmnAddrRangeIpAddrType InetAddressType,
    cGgsnPlmnAddrRangeFirstIp InetAddress,
    cGgsnPlmnAddrRangeLastIp InetAddress,
    cGgsnPlmnAddrRangeRowStatus RowStatus,
    cGgsnPlmnAddrRangeUsage INTEGER
    }

cGgsnPlmnAddrRangeIpAddrType OBJECT-TYPE
    SYNTAX InetAddressType
--    Rsyntax INTEGER {
--        ?? enum value of zero may cause problems
--        unknown(0),
--        ipv4(1),
--        ipv6(2),
--        dns(16)
--        }
    ACCESS not-accessible
    STATUS mandatory
    DESCRIPTION
        "The address type for cGgsnPlmnAddrRangeFirstIp and 
        cGgsnPlmnAddrRangeLastIp addresses. Only ipv4(1) addresses are
        supported."
    ::= { cGgsnPlmnIpAddrRangeEntry 1 }

cGgsnPlmnAddrRangeFirstIp OBJECT-TYPE
    SYNTAX InetAddress(SIZE(4..20))
--    Rsyntax OCTET STRING(SIZE(4..20))
    ACCESS not-accessible
    STATUS mandatory
    DESCRIPTION
        "First IP address in the address range."
    ::= { cGgsnPlmnIpAddrRangeEntry 2 }

cGgsnPlmnAddrRangeLastIp OBJECT-TYPE
    SYNTAX InetAddress(SIZE(4..20))
--    Rsyntax OCTET STRING(SIZE(4..20))
    ACCESS not-accessible
    STATUS mandatory
    DESCRIPTION
        "Last IP address in the address range."
    ::= { cGgsnPlmnIpAddrRangeEntry 3 }

cGgsnPlmnAddrRangeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an
        existing row in this table.
        
        To create a row, set this object to 'createAndGo'.
        To delete a row, set this object to 'destroy'.
        To modify a row, the row needs to be deleted and created fresh
        with new values."
    ::= { cGgsnPlmnIpAddrRangeEntry 4 }

cGgsnPlmnAddrRangeUsage OBJECT-TYPE
    SYNTAX INTEGER {
        security(1),
        sgsn(2)
        }
    ACCESS read-write
    STATUS mandatory
    DESCRIPTION
        "This object specifies how the address range will be used by 
        the GGSN.  
        
        When set to 'security', the address range is used for GGSN
        security feature i.e. any TPDU with destination address that
        falls in this address range will be discarded.
        
        When set to 'sgsn', the address range denotes the sgsn address
        range in the local PLMN which can be used to check roaming MS."
    DEFVAL { security }
    ::= { cGgsnPlmnIpAddrRangeEntry 5 }

cGgsnVersion OBJECT-TYPE
    SYNTAX INTEGER {
        release14(1),
        release30(2),
        release40(3),
        release31(4)
        }
    ACCESS read-only
    STATUS mandatory
    DESCRIPTION
        "This object specifies the which release of GPRS
        image is currently running on the GGSN."
    ::= { cGgsnStatus 1 }

cGgsnActiveNetworkInitPdps OBJECT-TYPE
    SYNTAX Gauge
--  Units
--    packets
    ACCESS read-only
    STATUS mandatory
    DESCRIPTION
        "This object represents the number of network initiated
        PDP contexts that are currently active."
    ::= { cGgsnStatus 2 }

cGgsnActivePppPdps OBJECT-TYPE
    SYNTAX Gauge
--  Units
--    packets
    ACCESS read-only
    STATUS mandatory
    DESCRIPTION
        "This object represents the number of PPP PDP contexts
         that are currently active."
    ::= { cGgsnStatus 3 }

cGgsnActivePppRegenPdps OBJECT-TYPE
    SYNTAX Gauge
--  Units
--    packets
    ACCESS read-only
    STATUS mandatory
    DESCRIPTION
        "This object represents the number of PPP-Regen PDP contexts
         that are currently active."
    ::= { cGgsnStatus 4 }

cGgsnPendingPppRegenPdps OBJECT-TYPE
    SYNTAX Gauge
--  Units
--    packets
    ACCESS read-only
    STATUS mandatory
    DESCRIPTION
        "This object represents the current number of pending 
        PPP regeneration sessions."
    ::= { cGgsnStatus 5 }

cGgsnActiveGtpVersion0Pdps OBJECT-TYPE
    SYNTAX Gauge
    ACCESS read-only
    STATUS mandatory
    DESCRIPTION
        "This object represents the current number of active GTP v0 PDP
        contexts."
    ::= { cGgsnStatus 6 }

cGgsnActiveGtpVersion1Pdps OBJECT-TYPE
    SYNTAX Gauge
    ACCESS read-only
    STATUS mandatory
    DESCRIPTION
        "This object represents the current number of active GTP v1 PDP
        contexts."
    ::= { cGgsnStatus 7 }

cGgsnGtpEncapInterface OBJECT-TYPE
    SYNTAX InterfaceIndexOrZero
--    Rsyntax INTEGER(0..2147483647)
    ACCESS read-only
    STATUS mandatory
    DESCRIPTION
        "This object represents the ifIndex of the interface on which
        which gtp encapsulation is configured. Only one interface can
        be configured with gtp encapsulation on the GGSN. A zero value
        indicates that no interface is configured with gtp 
        encapsulation."
    ::= { cGgsnStatus 8 }

cGgsnNotification TRAP-TYPE
-- Reverse mappable trap
    ENTERPRISE cGgsnNotifPrefix
    VARIABLES {
        cGgsnHistNotifType, cGgsnHistNotifSeverity, 
        cGgsnHistNotifTimestamp, cGgsnHistNotifGgsnIpAddrType, 
        cGgsnHistNotifGgsnIpAddr, cGgsnHistNotifInfo }
--  Status
--    mandatory
    DESCRIPTION
        "This notification indicates the occurrence of a GGSN 
        related alarm. If and when additional useful information
        is available for specific types of alarms, then that  
        information may be appended to the end of the
        notification in additional varbinds."
    ::= 1

cGgsnStatisticsGroup OBJECT IDENTIFIER ::= { cGgsnMIBGroups 1 }
-- OBJECT-GROUP
--  Status
--    mandatory
--  Descr
--     A collection of statistics on GGSN.
--  objects
--    cGgsnSentSigMessages, cGgsnReceivedSigMessages, 
--    cGgsnUnexpectedSigMessages, cGgsnSentGPDUs, 
--    cGgsnReceivedGPDUs, cGgsnSentGPDUOctets, 
--    cGgsnReceivedGPDUOctets, cGgsnUnexpectedGPDUs, 
--    cGgsnActivationRejectedPdps, cGgsnOutOfResourcePdps, 
--    cGgsnParserErrorMessages, cGgsnTotalCreatedPdps, 
--    cGgsnTotalDeletedPdps, cGgsnTotalNetworkInitPdps, 
--    cGgsnTotalPppPdpsCreated, cGgsnTotalPppPdpsDeleted, 
--    cGgsnOutOfResourcePppRegenPdps, cGgsnDroppedPppRegenPdps

cGgsnNotifMgmtGroup OBJECT IDENTIFIER ::= { cGgsnMIBGroups 2 }
-- OBJECT-GROUP
--  Status
--    mandatory
--  Descr
--     A collection of objects related with notification
--    management on GGSN.
--  objects
--    cGgsnNotifEnabled, cGgsnNotifLeastSeverLevel, 
--    cGgsnGeneratedNotifs, cGgsnIgnoredAlarms, 
--    cGgsnHistNotifMaxLength, cGgsnHistNotifLatestIndex, 
--    cGgsnHistNotifType, cGgsnHistNotifSeverity, 
--    cGgsnHistNotifTimestamp, cGgsnHistNotifGgsnIpAddrType, 
--    cGgsnHistNotifGgsnIpAddr, cGgsnHistNotifInfo

cGgsnConfigurationsGroup OBJECT IDENTIFIER ::= { cGgsnMIBGroups 3 }
-- OBJECT-GROUP
--  Status
--    deprecated
--  Descr
--     A collection of objects related with configurations on
--     GGSN. This is deprecated by cGgsnConfigurationsGroupRev1.
--  objects
--    cGgsnDefaultIpAllocationMethod, cGgsnIdlePdpPurgeTimer, 
--    cGgsnIpDupProtectRowStatus, cGgsnDefaultAggregRowStatus, 
--    cGgsnDefaultAaaAuthServerGroup, cGgsnDefaultAaaAccServerGroup, 
--    cGgsnPppVirtualTemplate, cGgsnPppRegenVirtualTemplate

cGgsnStatusGroup OBJECT IDENTIFIER ::= { cGgsnMIBGroups 5 }
-- OBJECT-GROUP
--  Status
--    mandatory
--  Descr
--     A collection of objects representing status on GGSN.
--  objects
--    cGgsnVersion, cGgsnActiveNetworkInitPdps, cGgsnActivePppPdps, 
--    cGgsnActivePppRegenPdps, cGgsnPendingPppRegenPdps

cGgsnConfigurationsGroupRev1 OBJECT IDENTIFIER ::= { cGgsnMIBGroups 6 }
-- OBJECT-GROUP
--  Status
--    mandatory
--  Descr
--     A collection of objects related with configurations on GGSN.
--  objects
--    cGgsnDefaultIpAllocationMethod, cGgsnIdlePdpPurgeTimer, 
--    cGgsnIpDupProtectRowStatus, cGgsnDefaultAggregRowStatus, 
--    cGgsnDefaultAaaAuthServerGroup, cGgsnDefaultAaaAccServerGroup, 
--    cGgsnPppVirtualTemplate, cGgsnPppRegenVirtualTemplate, 
--    cGgsnPlmnAddrRangeRowStatus

cGgsnUmtsGroup OBJECT IDENTIFIER ::= { cGgsnMIBGroups 7 }
-- OBJECT-GROUP
--  Status
--    mandatory
--  Descr
--     A collection of objects pertaining to GTP v1.
--  objects
--    cGgsnTftSemanticErrorPdps, cGgsnTftSyntacticErrorPdps, 
--    cGgsnPktFilterSemanticErrorPdps, 
--    cGgsnPktFilterSyntacticErrorPdps, cGgsnPlmnAddrRangeUsage, 
--    cGgsnActiveGtpVersion0Pdps, cGgsnActiveGtpVersion1Pdps, 
--    cGgsnGtpEncapInterface

cGgsnNotifGroup OBJECT IDENTIFIER ::= { cGgsnMIBGroups 4 }
-- NOTIFICATION-GROUP
--  Status
--    mandatory
--  Descr
--    A collection of notifications.
--  notifications
--    cGgsnNotification

cGgsnMIBCompliance OBJECT IDENTIFIER ::= { cGgsnMIBCompliances 1 }
-- MODULE-COMPLIANCE
--  Status
--    deprecated
--  Descr
--    The compliance statements for entities which
--    implement the CISCO GGSN MIB.
--    
--    This is deprecated by cGgsnMIBComplianceRev1.
--  Module
--    >>current<<
--   MandGroup
--    cGgsnStatisticsGroup
--   MandGroup
--    cGgsnNotifMgmtGroup
--   MandGroup
--    cGgsnConfigurationsGroup
--   MandGroup
--    cGgsnNotifGroup
--   MandGroup
--    cGgsnStatusGroup

cGgsnMIBComplianceRev1 OBJECT IDENTIFIER ::= { cGgsnMIBCompliances 2 }
-- MODULE-COMPLIANCE
--  Status
--    mandatory
--  Descr
--    The compliance statements for entities which
--    implement the CISCO GGSN MIB.
--  Module
--    >>current<<
--   MandGroup
--    cGgsnStatisticsGroup
--   MandGroup
--    cGgsnNotifMgmtGroup
--   MandGroup
--    cGgsnConfigurationsGroupRev1
--   MandGroup
--    cGgsnNotifGroup
--   MandGroup
--    cGgsnStatusGroup
--   OptGroup
--    cGgsnUmtsGroup
--   ObjVar
--    cGgsnHistNotifGgsnIpAddrType
--   ObjVar
--    cGgsnIpDupProtectRowStatus
--   ObjVar
--    cGgsnDefaultAggregRowStatus
--   ObjVar
--    cGgsnPlmnAddrRangeRowStatus


END
