-- MIB file created 31-Dec-2002 12:25:52, by
--   SMICng version 2.2.11-beta(PRO)(Solaris), January 20, 2001. Enterprise key cisco.com

CISCO-GGSN-QOS-MIB DEFINITIONS ::= BEGIN

-- From file: "CISCO-GGSN-QOS-MIB.my"
-- Compile options "4 7 F H N W 03 06 0B 0G 0N 0T"

IMPORTS
    ciscoMgmt
            FROM CISCO-SMI
    Gauge
            FROM RFC1155-SMI
    OBJECT-TYPE
            FROM RFC-1212;

cggsnQosMIB OBJECT IDENTIFIER ::= { ciscoMgmt 241 }
-- MODULE-IDENTITY
--  LastUpdated
--    200204181400Z
--  OrgName
--    Cisco Systems, Inc.
--  ContactInfo
--           Cisco Systems
--            Customer Service
--    
--    Postal: 170 W Tasman Drive
--            San Jose, CA  95134
--            USA
--    
--       Tel: +1 800 553-NETS
--    
--    E-mail: cs-gprs@cisco.com
--  Descr
--    This MIB module manages the Quality of Service 
--    parameters of GGSN in a GPRS system.
--    
--    GGSN is the Gateway GPRS Support Node in the GPRS
--    architecture. It provides interworking of GPRS 
--    network with external packet-switched networks 
--    - PDNs or other data networks.
--    
--    The following diagram illustrates a simplified GPRS
--    logical architecture with the name of inter-node
--    interface:
--    
--    +=============================================+
--    |                         +======+   a PLMN   |
--    |                         | SGSN |            |
--    |                         +======+            |
--    |                            |                |
--    |                            Gn               |
--    |                            |                |
--    |+====+   +====+ +=====+ +======+    +======+ |    +===+
--    || TE |-R-| MT |-| BSS |-| SGSN |-Gn-| GGSN |-|-Gi-|PDN|
--    |+====+   +====+ +=====+ +======+    +======+ |    +===+
--    |                                        |    |
--    |                                        |    |
--    +========================================|====+
--                                             Gp
--                                             |
--                    +=============================+
--                    | +====+   +=====+   +======+ |
--                    | | MS |===| BSS |===| SGSN | |
--                    | +====+   +=====+   +======+ |
--                    |                             |
--                    |                other PLMN   |
--                    +=============================+
--    
--    A PDP Context is an information set maintained by MS
--    and GSNs which describes the mobile wireless service
--    call or session.
--    
--    Three types of Qos mapping method are supported on GGSN:
--    canonical, delay and umts. Canonical Qos mapping 
--    consists of Best Effort, Normal and Premium Qos classes.
--    Delay Qos mapping consists of four classes: delay1, 
--    delay2, delay3 and delay-besteffort. UMTS QoS has the 
--    following traffic classes: signalling, conversational, 
--    streaming, interactive and background. UMTS QoS is 
--    based on differentiated services network model.
--    
--    A Qos Profile is associated with each PDP context which
--    defines multiple attributes like precedence, delay,
--    reliability, peak throughput, mean throughput and 
--    traffic class.  Based on the precedence, delay and mean
--    throughput an user is classified into different 
--    canonical and delay Qos classes .  Based on delay, 
--    jitter, bandwidth and reliability user is classified 
--    into the UMTS traffic classes.
--    
--    In GGSN, the QoS remapping mechanism is that, for 
--    uplink traffic, the GGSN remaps the TOS in the user 
--    traffic before forwarding the packet to the Gi 
--    interface and for downlink traffic, the GGSN will 
--    only setup the TOS for the IP header for the Tunnel, 
--    not the IP header for user traffic. Traffic from MS 
--    to PDN is considered as uplink and the reverse is 
--    considered as downlink traffic.
--    
--    Acronyms and terms:
--    
--     APN      Access Point Name
--     BSS      Base Station System
--     ETSI     European Telecommunications Standards Institute
--     DS       Differentiated Service 
--     DSCP     DS Code Point
--     GGSN     Gateway GPRS Support Node
--     GPRS     General Packet Radio Service
--     GSM      Global System for Mobile communication
--     GSN      GPRS Support Node
--     G-PDU    GTP PDU
--     MS       Mobile Station
--     MT       Mobile Terminal
--     PDN      Packet Data Network
--     PDP      Packet Data Protocol
--     PDU      Protocol Data Unit
--     PHB      Per-hop Behavior
--     PLMN     Public Land Mobile Network
--     SGSN     Serving GPRS support Node
--     TE       Terminal Equipment
--     T-PDU    the payload of G-PDU
--     UMTS     Universal Mobile Telecommunication System
--    
--    REFERENCE
--    
--    [1] GSM 03.60: Digital cellular telecommunications
--        system (Phase 2+); General Packet Radio Service
--        (GPRS); Service description; Stage 2. V7.1.0
--    
--    [2] GSM 09.60: Digital cellular telecommunication
--        system (Phase 2+); General Packet Radio Service
--        (GPRS); GPRS Tunnelling Protocol (GTP) across
--        Gn and Gp Interface. V7.3.0
--    
--    [3] 3GPP; Technical Specification Group Services
--        and System Aspects; QoS Concept and Architecture.
--        3G TS 23.107 v3.2.0.
--    
--    [4] 3GPP; Technical Specification Group Core Network;
--        General Packet Radio Service(GPRS); GPRS 
--        Tunnelling Protocol (GTP) across Gn and Gp 
--        Interface (Release 1999). 3G TS 29.060 v3.5.0.
--    
--    [5] 3GPP; Technical Specification Group Services
--        and System Aspects; General Packet Radio 
--        Service(GPRS); Service description; Stage 2 
--        (Release 1999) 3G TS 23.060 v3.3.1.
--  RevDate
--    200204181400Z
--  RevDescr
--    
--    Added the enumeration 'umts' to 
--    cggsnQosMappingMethod.
--    
--    Added the following objects:
--    cggsnQosUmtsTrafficClass,
--    cggsnQosUmtsDiffServPhbgroup, cggsnQosUmtsPdps,
--    cggsnQosDiffServPhb, cggsnQosDscp and 
--    cggsnQosUmtsDscpUnmodified.
--  RevDate
--    200112061330Z
--  RevDescr
--    Initial version of this MIB module.

cggsnQosMIBObjects OBJECT IDENTIFIER ::= { cggsnQosMIB 1 }
cggsnQosGeneralConfig OBJECT IDENTIFIER ::= { cggsnQosMIBObjects 1 }
cggsnQosCanonicalQos OBJECT IDENTIFIER ::= { cggsnQosMIBObjects 2 }
cggsnQosUmtsQos OBJECT IDENTIFIER ::= { cggsnQosMIBObjects 3 }
cggsnQosMIBConformances OBJECT IDENTIFIER ::= { cggsnQosMIB 2 }
cggsnQosMIBCompliances OBJECT IDENTIFIER ::= { cggsnQosMIBConformances 1 }
cggsnQosMIBGroups OBJECT IDENTIFIER ::= { cggsnQosMIBConformances 2 }

cggsnQosMappingMethod OBJECT-TYPE
    SYNTAX INTEGER {
        none(1),
        canonical(2),
        delay(3),
        umts(4)
        }
    ACCESS read-write
    STATUS mandatory
    DESCRIPTION
        "This object specifies the type of QoS method (canonical
         or delay or none (best-effort) or umts) mapped to GPRS QoS."
    DEFVAL { none }
    ::= { cggsnQosGeneralConfig 1 }

cggsnQosClassIpTosMapTable OBJECT-TYPE
    SYNTAX SEQUENCE OF CggsnQosClassIpTosMapEntry
    ACCESS not-accessible
    STATUS mandatory
    DESCRIPTION
        "This table represents the mapping for different 
         Qos classes to TOS precedence classes in the IP 
         header. 
        
         If cggsnQosMappingMethod is set to delay(3),
         the length of the table is 4 with the following 
         default mapping: delay1 = 3 (flash), delay2 = 2 (immediate),
         delay3 = 1 (priority), delay_besteffort = 0 (routine).
        
         If cggsnQosMappingMethod is set to canonical(2),
         the length of the table is 3 with the following 
         default mapping: premium = 2 (immediate), normal
         = 1 (priority), best_effort = 0 (routine).
          
         If cggsnQosMappingMethod is set to umts(4) or none(1),
         the table will be empty."
    ::= { cggsnQosGeneralConfig 2 }

cggsnQosClassIpTosMapEntry OBJECT-TYPE
    SYNTAX CggsnQosClassIpTosMapEntry
    ACCESS not-accessible
    STATUS mandatory
    DESCRIPTION
        "Entry which denotes mapping of different Qos classes 
        to TOS precedence class and also the number of PDP
        contexts associated with each Qos Class."
    INDEX { cggsnQosClass }
    ::= { cggsnQosClassIpTosMapTable 1 }

CggsnQosClassIpTosMapEntry ::= SEQUENCE {
    cggsnQosClass INTEGER,
    cggsnQosMappedIpTos INTEGER,
    cggsnQosCurrentPdps Gauge
    }

cggsnQosClass OBJECT-TYPE
    SYNTAX INTEGER(1..4)
    ACCESS not-accessible
    STATUS mandatory
    DESCRIPTION
        "This object specifies different Qos Classes of
        either 'canonical' or 'delay' Qos based on the 
        value set to cggsnQosMappingMethod. The following
        is how the value needs to be interpreted.
        
        If cggsnQosMappingMethod is set to delay(3),
        1 - delay1, 2 - delay2, 3 - delay3, 
        4 - delay_best_effort.
        
        If cggsnQosMappingMethod is set to canonical(2),
        1 - premium, 2 - normal, 3 - best_effort."
    ::= { cggsnQosClassIpTosMapEntry 1 }

cggsnQosMappedIpTos OBJECT-TYPE
    SYNTAX INTEGER(0..5)
    ACCESS read-write
    STATUS mandatory
    DESCRIPTION
        "This object specifies the IP TOS precedence to which
        cggsnQosClass is mapped. Higher TOS precedence
        value indicates a higher service priority. The values
        '6 (internetwork_control)' and '7 (network_control)' 
        of TOS are not used in mapping."
    ::= { cggsnQosClassIpTosMapEntry 2 }

cggsnQosCurrentPdps OBJECT-TYPE
    SYNTAX Gauge
    ACCESS read-only
    STATUS mandatory
    DESCRIPTION
        "This object specifies the current number of PDP contexts
         that have cggsnQosClass."
    ::= { cggsnQosClassIpTosMapEntry 3 }

cggsnQosTotalBandwidthResrc OBJECT-TYPE
    SYNTAX Gauge(1..4294967295)
--  Units
--    bits/sec
    ACCESS read-write
    STATUS mandatory
    DESCRIPTION
        "The total amount of bandwidth resource on the GGSN,
         this total depends on various factors like system
         throughput, memory size, maximum number of PDP contexts
         supported.  A portion of the total resources will be
         allocated to a user at the PDP context activation time
         based on the Qos class the user is assigned to. This
         object can only be retrieved if cggsnQosMappingMethod 
         is set to canonical(2)."
    ::= { cggsnQosCanonicalQos 1 }

cggsnQosCurrentUsedBandwidth OBJECT-TYPE
    SYNTAX Gauge
--  Units
--    bits/sec
    ACCESS read-only
    STATUS mandatory
    DESCRIPTION
        "The current amount of bandwidth resource used on the GGSN.
         This object can only be retrieved if cggsnQosMappingMethod
         is set to canonical(2)."
    ::= { cggsnQosCanonicalQos 2 }

cggsnQosPremiumMtDeviationFactor OBJECT-TYPE
    SYNTAX Gauge(1..1000)
    ACCESS read-write
    STATUS mandatory
    DESCRIPTION
        "This object specifies the mean throughput deviation
        factor that the GGSN uses to calculate the allowable
        data throughput for Premium Qos. This object can
        only be retrieved if cggsnQosMappingMethod is set
        to canonical(2)."
    DEFVAL { 100 }
    ::= { cggsnQosCanonicalQos 3 }

cggsnQosBestEffrtBandWidthFactor OBJECT-TYPE
    SYNTAX Gauge(1..4000000)
--  Units
--    bits/sec
    ACCESS read-write
    STATUS mandatory
    DESCRIPTION
        "This object specifies the bandwidth factor to be 
        applied to canonical best-effort QoS class. This 
        object can only be retrieved if cggsnQosMappingMethod 
        is set to canonical(2)."
    DEFVAL { 10 }
    ::= { cggsnQosCanonicalQos 4 }

cggsnQosPremiumMeanThroughput OBJECT-TYPE
    SYNTAX Gauge
--  Units
--    bytes/sec
    ACCESS read-only
    STATUS mandatory
    DESCRIPTION
        "The sum of the mean throughput of premium class QOS
         users on the GSN. This object can only be retrieved
         if cggsnQosMappingMethod is set to canonical(2)."
    ::= { cggsnQosCanonicalQos 5 }

cggsnQosNormalMeanThroughput OBJECT-TYPE
    SYNTAX Gauge
--  Units
--    bytes/sec
    ACCESS read-only
    STATUS mandatory
    DESCRIPTION
        "The sum of the mean throughput of normal class QOS
         users on the GSN. This object can only be retrieved
         if cggsnQosMappingMethod is set to canonical(2)."
    ::= { cggsnQosCanonicalQos 6 }

cggsnQosBestEffortMeanThroughput OBJECT-TYPE
    SYNTAX Gauge
--  Units
--    bytes/sec
    ACCESS read-only
    STATUS mandatory
    DESCRIPTION
        "The sum of the mean throughput of best-effort class
         QOS users on the GSN. This object can only be retrieved
         if cggsnQosMappingMethod is set to canonical(2)."
    ::= { cggsnQosCanonicalQos 7 }

cggsnQosTrafficClassPhbTable OBJECT-TYPE
    SYNTAX SEQUENCE OF CggsnQosTrafficClassPhbEntry
    ACCESS not-accessible
    STATUS mandatory
    DESCRIPTION
        "This table represents the mapping between a given traffic 
        class and the corresponding DS PHB group. 
        
        The table has one entry for each possible traffic class type.
        
        The table will be empty if the cggsnQosMappingMethod is not 
        set to 'umts'."
    ::= { cggsnQosUmtsQos 1 }

cggsnQosTrafficClassPhbEntry OBJECT-TYPE
    SYNTAX CggsnQosTrafficClassPhbEntry
    ACCESS not-accessible
    STATUS mandatory
    DESCRIPTION
        "Entry which denotes mapping between a given traffic 
        class and the corresponding DS PHB group and the number 
        of PDP contexts associated with each traffic class."
    INDEX { cggsnQosUmtsTrafficClass }
    ::= { cggsnQosTrafficClassPhbTable 1 }

CggsnQosTrafficClassPhbEntry ::= SEQUENCE {
    cggsnQosUmtsTrafficClass INTEGER,
    cggsnQosUmtsDiffServPhbgroup INTEGER,
    cggsnQosUmtsPdps Gauge
    }

cggsnQosUmtsTrafficClass OBJECT-TYPE
    SYNTAX INTEGER {
        signalling(1),
        conversational(2),
        streaming(3),
        interactive(4),
        background(5)
        }
    ACCESS not-accessible
    STATUS mandatory
    DESCRIPTION
        "This object denotes the UMTS QoS traffic class.  UMTS QoS
        uses this parameter to make assumptions about the traffic 
        source, and determine the maximum bitrate, and guaranteed 
        bitrate for the traffic class when performing admission 
        control. The signalling traffic class only applies to the 
        UMTS signalling messages.  "
    ::= { cggsnQosTrafficClassPhbEntry 1 }

cggsnQosUmtsDiffServPhbgroup OBJECT-TYPE
    SYNTAX INTEGER {
        signallingClass(1),
        efClass(2),
        afClass1(3),
        afClass2(4),
        afClass3(5),
        afClass4(6),
        bestEffort(7)
        }
    ACCESS read-write
    STATUS mandatory
    DESCRIPTION
        "This object denotes the PHB which is mapped to the traffic
        class given by cggsnQosUmtsTrafficClass.
        
        DS architecture is based on number of functional elements,
        one of which is PHB.  PHBs specify queuing, queue management 
        and scheduling characteristics that allow a means of 
        allocating buffer and bandwidth resources at each node among 
        the competing traffic streams.
        
        The various DS PHBs include:
                signalling - signallingClass(1)
                The signalling class PHB is only used for the UMTS 
                signalling messages. This DS PHB does not apply to 
                any other IP data packets.
        
                expedited forwarding - efClass(2)
                The expedited forwarding PHB is used for providing 
                a low loss, low latency, low jitter, assured 
                bandwidth, end-to-end service through the DS domains. 
                Such a service appears to the endpoints like a 
                point-to-point connection, or a virtual leased line.
        
                assured forwarding - afClass(3-6)
                The assured forwarding PHB provides a means for a 
                provider DS domain to offer different levels of 
                delivery assurances for packets received from a 
                customer DS domain. Four assured forwarding classes: 
                afClass1, afClass2, afClass3 and afClass4 are defined,
                where each AF class is in each DS node allocated a
                certain amouont of forwarding resoources(buffer space
                and bandwidth). IP packets are assigned into one or 
                more of these classes, according to the subscribed 
                service.  Within each class the packets are marked 
                by a mobile subscriber, or by the provider DS domain,
                with one of the three possible drop precedence 
                values. In case of congestion, the drop precedence 
                of a packet determines the relative importance of a 
                packet within the class. Packets in one class are 
                forwarded independently of the packets in another 
                class.
        
                best effort - bestEffort(7)
                This is the default PHB.  The packets of this 
                aggregate are forwarded on an output link whenever
                the link is not required to satisfy any other PHB.
                "
    DEFVAL { bestEffort }
    ::= { cggsnQosTrafficClassPhbEntry 2 }

cggsnQosUmtsPdps OBJECT-TYPE
    SYNTAX Gauge
    ACCESS read-only
    STATUS mandatory
    DESCRIPTION
        "This object specifies the current number of PDP contexts
         associated with each traffic class identified by
         cggsnQosUmtsTrafficClass."
    ::= { cggsnQosTrafficClassPhbEntry 3 }

cggsnQosPhbToDscpMapTable OBJECT-TYPE
    SYNTAX SEQUENCE OF CggsnQosPhbToDscpMapEntry
    ACCESS not-accessible
    STATUS mandatory
    DESCRIPTION
        "This table represents the DiffServ Code Point (DSCP) 
        mappings for different types of DiffServ PHB groups. 
        
        The table has one entry for each possible DS PHB."
    ::= { cggsnQosUmtsQos 2 }

cggsnQosPhbToDscpMapEntry OBJECT-TYPE
    SYNTAX CggsnQosPhbToDscpMapEntry
    ACCESS not-accessible
    STATUS mandatory
    DESCRIPTION
        "Entry which denotes mapping of different DS PHBs to the 
        DSCP."
    INDEX { cggsnQosDiffServPhb }
    ::= { cggsnQosPhbToDscpMapTable 1 }

CggsnQosPhbToDscpMapEntry ::= SEQUENCE {
    cggsnQosDiffServPhb INTEGER,
    cggsnQosDscp INTEGER
    }

cggsnQosDiffServPhb OBJECT-TYPE
    SYNTAX INTEGER {
        signallingClass(1),
        efClass(2),
        afClass1Low(3),
        afClass1Medium(4),
        afClass1High(5),
        afClass2Low(6),
        afClass2Medium(7),
        afClass2High(8),
        afClass3Low(9),
        afClass3Medium(10),
        afClass3High(11),
        afClass4Low(12),
        afClass4Medium(13),
        afClass4High(14),
        bestEffort(15)
        }
    ACCESS not-accessible
    STATUS mandatory
    DESCRIPTION
        "This object denotes the various possible values of PHB.
        
         It can take up one of the foll: values -
            signallingClass(1) - Signalling class
            efClass(2) - expedited forwarding class
            afClass1Low(3) - assured forwarding class 1
                             low drop precedence
            afClass1Medium(4) - assured forwarding class 1
                             medium drop precedence
            afClass1High(5) - assured forwarding class 1
                             high drop precedence
            afClass2Low(6) - assured forwarding class 2
                             low drop precedence
            afClass2Medium(7) - assured forwarding class 2
                             medium drop precedence
            afClass2High(8) - assured forwarding class 2
                             high drop precedence
            afClass3Low(9) - assured forwarding class 3
                             low drop precedence
            afClass3Medium(10) - assured forwarding class 3
                             medium drop precedence
            afClass3High(11) - assured forwarding class 3
                             high drop precedence
            afClass4Low(12) - assured forwarding class 4
                             low drop precedence
            afClass4Medium(13) - assured forwarding class 4
                             medium drop precedence
            afClass4High(14) - assured forwarding class 4
                             high drop precedence
            bestEffort(15) - best effort class"
    ::= { cggsnQosPhbToDscpMapEntry 1 }

cggsnQosDscp OBJECT-TYPE
    SYNTAX INTEGER(0..63)
    ACCESS read-write
    STATUS mandatory
    DESCRIPTION
        "This object denotes the DSCP for the corresponding PHB
        defined by cggsnQosDiffServPhb.
        
        The values recommended for the various values of 
        cggsnQosDiffServPhb are:
            signallingClass - '101000'
            efClass         - '101110'
            afClass1Low     - '001010'
            afClass1Medium  - '001100'
            afClass1High    - '001110'
            afClass2Low     - '010010'
            afClass2Medium  - '010100'
            afClass2High    - '010110'
            afClass3Low     - '011010'
            afClass3Medium  - '011100'
            afClass3High    - '011110'
            afClass4Low     - '100010'
            afClass4Medium  - '100100'
            afClass4High    - '100110'
            bestEffort      - '000000'"
    ::= { cggsnQosPhbToDscpMapEntry 2 }

cggsnQosUmtsDscpUnmodified OBJECT-TYPE
    SYNTAX INTEGER {
        up(1),
        down(2),
        all(3),
        none(4)
        }
    ACCESS read-write
    STATUS mandatory
    DESCRIPTION
        "This object defines if the DSCP in the subscriber datagram
         will be forwarded in the uplink/downlink path with or without
         modification.
        
         The various values that this object can take up are:
                up(1) - DSCP will not be modified in the uplink 
                        path alone
                down(2) - DSCP will not be modified in downlink 
                         path alone
                all(3) - DSCP will not be modified in both 
                         uplink/downlink path
                none(4) - DSCP will be modified both in uplink and 
                         in downlink path"
    DEFVAL { none }
    ::= { cggsnQosUmtsQos 3 }

cggsnQosGeneralConfigGroup OBJECT IDENTIFIER ::= { cggsnQosMIBGroups 1 }
-- OBJECT-GROUP
--  Status
--    mandatory
--  Descr
--    A collection of objects providing general Qos 
--    configurations.
--  objects
--    cggsnQosMappingMethod, cggsnQosMappedIpTos, 
--    cggsnQosCurrentPdps

cggsnQosCanonicalQosGroup OBJECT IDENTIFIER ::= { cggsnQosMIBGroups 2 }
-- OBJECT-GROUP
--  Status
--    mandatory
--  Descr
--    A collection of objects specific to Canonical Qos
--    on GGSN.
--  objects
--    cggsnQosTotalBandwidthResrc, cggsnQosCurrentUsedBandwidth, 
--    cggsnQosPremiumMtDeviationFactor, 
--    cggsnQosBestEffrtBandWidthFactor, 
--    cggsnQosPremiumMeanThroughput, cggsnQosNormalMeanThroughput, 
--    cggsnQosBestEffortMeanThroughput

cggsnQosUmtsQosGroup OBJECT IDENTIFIER ::= { cggsnQosMIBGroups 3 }
-- OBJECT-GROUP
--  Status
--    mandatory
--  Descr
--    A collection of objects pertaining to the Umts Qos on
--    GGSN.
--  objects
--    cggsnQosUmtsDiffServPhbgroup, cggsnQosUmtsPdps, cggsnQosDscp, 
--    cggsnQosUmtsDscpUnmodified

cggsnQosMIBCompliance OBJECT IDENTIFIER ::= { cggsnQosMIBCompliances 1 }
-- MODULE-COMPLIANCE
--  Status
--    deprecated
--  Descr
--    The compliance statements for entities which
--    implement the CISCO GGSN QOS MIB.
--    
--    This compliance has been deprecated by 
--    cggsnQosMIBComplianceRev1.
--  Module
--    >>current<<
--   MandGroup
--    cggsnQosGeneralConfigGroup
--   MandGroup
--    cggsnQosCanonicalQosGroup

cggsnQosMIBComplianceRev1 OBJECT IDENTIFIER ::= { cggsnQosMIBCompliances 2 }
-- MODULE-COMPLIANCE
--  Status
--    mandatory
--  Descr
--    The compliance statements for entities which
--    implement the CISCO GGSN QOS MIB.
--  Module
--    >>current<<
--   MandGroup
--    cggsnQosGeneralConfigGroup
--   MandGroup
--    cggsnQosCanonicalQosGroup
--   MandGroup
--    cggsnQosUmtsQosGroup


END
