-- MIB file created 27-Dec-2002 15:11:19, by
--   SMICng version 2.2.11-beta(PRO)(Solaris), January 20, 2001. Enterprise key cisco.com

CISCO-ENTITY-VENDORTYPE-OID-MIB DEFINITIONS ::= BEGIN

-- From file: "CISCO-ENTITY-VENDORTYPE-OID-MIB.my"
-- Compile options "4 7 F H N W 03 06 0B 0G 0N 0T"

IMPORTS
    ciscoModules
            FROM CISCO-SMI;

ciscoEntityVendortypeOIDMIB OBJECT IDENTIFIER ::= { ciscoModules 3 }
-- MODULE-IDENTITY
--  LastUpdated
--    200204051400Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines the object identifiers that are
--    assigned to various components on cisco products,
--    which are used by the entPhysicalTable of the ENTITY-MIB
--    to uniquely identify the type of each physical entry.
--  RevDate
--    200204051400Z
--  RevDescr
--    CANA Assignments.
--  RevDate
--    9708051930Z
--  RevDescr
--    Miscellaneous updates.

cevMIBObjects   OBJECT IDENTIFIER ::= { ciscoEntityVendortypeOIDMIB 1 }
cevOther        OBJECT IDENTIFIER ::= { cevMIBObjects 1 }
cevOtherUnknownCard OBJECT IDENTIFIER ::= { cevOther 1 }
cevUnknown      OBJECT IDENTIFIER ::= { cevMIBObjects 2 }
cevChassis      OBJECT IDENTIFIER ::= { cevMIBObjects 3 }
cevChassisUnknown OBJECT IDENTIFIER ::= { cevChassis 1 }
cevChassis2000  OBJECT IDENTIFIER ::= { cevChassis 2 }
cevChassis2500  OBJECT IDENTIFIER ::= { cevChassis 3 }
cevChassis2501  OBJECT IDENTIFIER ::= { cevChassis 4 }
cevChassis2502  OBJECT IDENTIFIER ::= { cevChassis 5 }
cevChassis2503  OBJECT IDENTIFIER ::= { cevChassis 6 }
cevChassis2504  OBJECT IDENTIFIER ::= { cevChassis 7 }
cevChassis2505  OBJECT IDENTIFIER ::= { cevChassis 8 }
cevChassis2506  OBJECT IDENTIFIER ::= { cevChassis 9 }
cevChassis2507  OBJECT IDENTIFIER ::= { cevChassis 10 }
cevChassis2508  OBJECT IDENTIFIER ::= { cevChassis 11 }
cevChassis2509  OBJECT IDENTIFIER ::= { cevChassis 12 }
cevChassis2510  OBJECT IDENTIFIER ::= { cevChassis 13 }
cevChassis2511  OBJECT IDENTIFIER ::= { cevChassis 14 }
cevChassis2512  OBJECT IDENTIFIER ::= { cevChassis 15 }
cevChassis2513  OBJECT IDENTIFIER ::= { cevChassis 16 }
cevChassis2514  OBJECT IDENTIFIER ::= { cevChassis 17 }
cevChassis2515  OBJECT IDENTIFIER ::= { cevChassis 18 }
cevChassis2516  OBJECT IDENTIFIER ::= { cevChassis 19 }
cevChassis2517  OBJECT IDENTIFIER ::= { cevChassis 20 }
cevChassis2518  OBJECT IDENTIFIER ::= { cevChassis 21 }
cevChassis2519  OBJECT IDENTIFIER ::= { cevChassis 22 }
cevChassis2520  OBJECT IDENTIFIER ::= { cevChassis 23 }
cevChassis2521  OBJECT IDENTIFIER ::= { cevChassis 24 }
cevChassis2522  OBJECT IDENTIFIER ::= { cevChassis 25 }
cevChassis2523  OBJECT IDENTIFIER ::= { cevChassis 26 }
cevChassis2524  OBJECT IDENTIFIER ::= { cevChassis 27 }
cevChassis2525  OBJECT IDENTIFIER ::= { cevChassis 28 }
cevChassis3000  OBJECT IDENTIFIER ::= { cevChassis 29 }
cevChassis3104  OBJECT IDENTIFIER ::= { cevChassis 30 }
cevChassis3204  OBJECT IDENTIFIER ::= { cevChassis 31 }
cevChassisIGS   OBJECT IDENTIFIER ::= { cevChassis 32 }
cevChassis2501LANFRADFX OBJECT IDENTIFIER ::= { cevChassis 33 }
cevChassis2501FRADFX OBJECT IDENTIFIER ::= { cevChassis 34 }
cevChassis2502LANFRADFX OBJECT IDENTIFIER ::= { cevChassis 35 }
cevChassisWSX3011 OBJECT IDENTIFIER ::= { cevChassis 36 }
cevChassisAccessProEC OBJECT IDENTIFIER ::= { cevChassis 37 }
cevChassisAccessProRC OBJECT IDENTIFIER ::= { cevChassis 38 }
cevChassisWSX5301 OBJECT IDENTIFIER ::= { cevChassis 39 }
cevChassisAS2509RJ OBJECT IDENTIFIER ::= { cevChassis 40 }
cevChassisAS2511RJ OBJECT IDENTIFIER ::= { cevChassis 41 }
cevChassis3800  OBJECT IDENTIFIER ::= { cevChassis 42 }
cevChassis3620  OBJECT IDENTIFIER ::= { cevChassis 43 }
cevChassis3640  OBJECT IDENTIFIER ::= { cevChassis 44 }
cevChassis7204  OBJECT IDENTIFIER ::= { cevChassis 45 }
cevChassis7206  OBJECT IDENTIFIER ::= { cevChassis 46 }
cevChassisAS5300 OBJECT IDENTIFIER ::= { cevChassis 47 }
cevChassisAs5800RS OBJECT IDENTIFIER ::= { cevChassis 49 }
cevChassisAs5800DS OBJECT IDENTIFIER ::= { cevChassis 50 }
cevChassis7202  OBJECT IDENTIFIER ::= { cevChassis 51 }
cevChassisRpm   OBJECT IDENTIFIER ::= { cevChassis 52 }
cevChassis1710  OBJECT IDENTIFIER ::= { cevChassis 53 }
cevChassis1720  OBJECT IDENTIFIER ::= { cevChassis 54 }
cevChassisCat8540Msr OBJECT IDENTIFIER ::= { cevChassis 55 }
cevChassisCat8540Csr OBJECT IDENTIFIER ::= { cevChassis 56 }
cevChassisUbr7246 OBJECT IDENTIFIER ::= { cevChassis 57 }
cevChassis7576  OBJECT IDENTIFIER ::= { cevChassis 58 }
cevChassis3660  OBJECT IDENTIFIER ::= { cevChassis 59 }
cevChassis1401  OBJECT IDENTIFIER ::= { cevChassis 60 }
cevChassis2613  OBJECT IDENTIFIER ::= { cevChassis 61 }
cevChassis2610  OBJECT IDENTIFIER ::= { cevChassis 62 }
cevChassis2612  OBJECT IDENTIFIER ::= { cevChassis 63 }
cevChassis2611  OBJECT IDENTIFIER ::= { cevChassis 64 }
cevChassis2620  OBJECT IDENTIFIER ::= { cevChassis 65 }
cevChassis2621  OBJECT IDENTIFIER ::= { cevChassis 66 }
cevChassisCat8510Csr OBJECT IDENTIFIER ::= { cevChassis 67 }
cevChassisUbr7223 OBJECT IDENTIFIER ::= { cevChassis 68 }
cevChassis6400Nrp OBJECT IDENTIFIER ::= { cevChassis 69 }
cevChassis801   OBJECT IDENTIFIER ::= { cevChassis 70 }
cevChassis802   OBJECT IDENTIFIER ::= { cevChassis 71 }
cevChassis803   OBJECT IDENTIFIER ::= { cevChassis 72 }
cevChassis804   OBJECT IDENTIFIER ::= { cevChassis 73 }
cevChassis7206Vxr OBJECT IDENTIFIER ::= { cevChassis 74 }
cevChassis7204Vxr OBJECT IDENTIFIER ::= { cevChassis 75 }
cevChassis1750  OBJECT IDENTIFIER ::= { cevChassis 76 }
cevChassisCat2924XLv OBJECT IDENTIFIER ::= { cevChassis 77 }
cevChassisCat2924CXLv OBJECT IDENTIFIER ::= { cevChassis 78 }
cevChassisCat2912XL OBJECT IDENTIFIER ::= { cevChassis 79 }
cevChassisCat2924MXL OBJECT IDENTIFIER ::= { cevChassis 80 }
cevChassisCat2912MfXL OBJECT IDENTIFIER ::= { cevChassis 81 }
cevChassis1538M OBJECT IDENTIFIER ::= { cevChassis 82 }
cevChassis1548M OBJECT IDENTIFIER ::= { cevChassis 83 }
cevChassisFasthub100 OBJECT IDENTIFIER ::= { cevChassis 84 }
cevChassisPIXFirewall OBJECT IDENTIFIER ::= { cevChassis 85 }
cevChassisMGX8850 OBJECT IDENTIFIER ::= { cevChassis 86 }
cevChassisMGX8820 OBJECT IDENTIFIER ::= { cevChassis 87 }
cevChassisCat8510Msr OBJECT IDENTIFIER ::= { cevChassis 88 }
cevChassisCat8515Msr OBJECT IDENTIFIER ::= { cevChassis 89 }
cevChassisIGX8410 OBJECT IDENTIFIER ::= { cevChassis 90 }
cevChassisIGX8420 OBJECT IDENTIFIER ::= { cevChassis 91 }
cevChassisIGX8430 OBJECT IDENTIFIER ::= { cevChassis 92 }
cevChassisIGX8450 OBJECT IDENTIFIER ::= { cevChassis 93 }
cevChassisBPX8620 OBJECT IDENTIFIER ::= { cevChassis 95 }
cevChassisBPX8650 OBJECT IDENTIFIER ::= { cevChassis 96 }
cevChassisBPX8680 OBJECT IDENTIFIER ::= { cevChassis 97 }
cevChassisCacheEngine OBJECT IDENTIFIER ::= { cevChassis 98 }
cevChassisCat6000 OBJECT IDENTIFIER ::= { cevChassis 99 }
cevChassisMC3810 OBJECT IDENTIFIER ::= { cevChassis 100 }
cevChassisIGXSes OBJECT IDENTIFIER ::= { cevChassis 102 }
cevChassisLocalDirector OBJECT IDENTIFIER ::= { cevChassis 103 }
cevChassis805   OBJECT IDENTIFIER ::= { cevChassis 104 }
cevChassisCat3508GXL OBJECT IDENTIFIER ::= { cevChassis 105 }
cevChassisCat3512XL OBJECT IDENTIFIER ::= { cevChassis 106 }
cevChassisCat3524XL OBJECT IDENTIFIER ::= { cevChassis 107 }
cevChassisCat2908XL OBJECT IDENTIFIER ::= { cevChassis 108 }
cevChassisCat2916MXL OBJECT IDENTIFIER ::= { cevChassis 109 }
cevChassis1417  OBJECT IDENTIFIER ::= { cevChassis 111 }
cevChassisOpticalRegenerator OBJECT IDENTIFIER ::= { cevChassis 112 }
cevChassisCat2924XL OBJECT IDENTIFIER ::= { cevChassis 116 }
cevChassisCat2924CXL OBJECT IDENTIFIER ::= { cevChassis 117 }
cevChassisUbr924 OBJECT IDENTIFIER ::= { cevChassis 118 }
cevChassisWsX6302Msm OBJECT IDENTIFIER ::= { cevChassis 119 }
cevChassisCat5kRsfc OBJECT IDENTIFIER ::= { cevChassis 120 }
cevChassis7120Quadt1 OBJECT IDENTIFIER ::= { cevChassis 122 }
cevChassis7120T3 OBJECT IDENTIFIER ::= { cevChassis 123 }
cevChassis7120E3 OBJECT IDENTIFIER ::= { cevChassis 124 }
cevChassis7120At3 OBJECT IDENTIFIER ::= { cevChassis 125 }
cevChassis7120Ae3 OBJECT IDENTIFIER ::= { cevChassis 126 }
cevChassis7120Smi3 OBJECT IDENTIFIER ::= { cevChassis 127 }
cevChassis7140Dualt3 OBJECT IDENTIFIER ::= { cevChassis 128 }
cevChassis7140Duale3 OBJECT IDENTIFIER ::= { cevChassis 129 }
cevChassis7140Dualat3 OBJECT IDENTIFIER ::= { cevChassis 130 }
cevChassis7140Dualae3 OBJECT IDENTIFIER ::= { cevChassis 131 }
cevChassis7140Dualmm3 OBJECT IDENTIFIER ::= { cevChassis 132 }
cevChassis12016 OBJECT IDENTIFIER ::= { cevChassis 136 }
cevChassis7140Octt1 OBJECT IDENTIFIER ::= { cevChassis 138 }
cevChassis7140Dualfe OBJECT IDENTIFIER ::= { cevChassis 139 }
cevChassisCat3548XL OBJECT IDENTIFIER ::= { cevChassis 140 }
cevChassisAS5200 OBJECT IDENTIFIER ::= { cevChassis 146 }
cevChassis12008 OBJECT IDENTIFIER ::= { cevChassis 147 }
cevChassis12012 OBJECT IDENTIFIER ::= { cevChassis 148 }
cevChassisMc3810V3 OBJECT IDENTIFIER ::= { cevChassis 149 }
cevChassis7507z OBJECT IDENTIFIER ::= { cevChassis 151 }
cevChassis7513z OBJECT IDENTIFIER ::= { cevChassis 152 }
cevChassis7507mx OBJECT IDENTIFIER ::= { cevChassis 153 }
cevChassis7513mx OBJECT IDENTIFIER ::= { cevChassis 154 }
cevChassisUbr912C OBJECT IDENTIFIER ::= { cevChassis 155 }
cevChassisUbr912S OBJECT IDENTIFIER ::= { cevChassis 156 }
cevChassisUbr914 OBJECT IDENTIFIER ::= { cevChassis 157 }
cevChassisCat2948gL3 OBJECT IDENTIFIER ::= { cevChassis 161 }
cevChassisCat4232L3 OBJECT IDENTIFIER ::= { cevChassis 164 }
cevChassisOpticalRegeneratorDCPower OBJECT IDENTIFIER ::= { cevChassis 165 }
cevChassisCVA122 OBJECT IDENTIFIER ::= { cevChassis 171 }
cevChassisCVA124 OBJECT IDENTIFIER ::= { cevChassis 172 }
cevChassisMGX8240 OBJECT IDENTIFIER ::= { cevChassis 176 }
cevChassisMGX8950 OBJECT IDENTIFIER ::= { cevChassis 181 }
cevChassisUbr925 OBJECT IDENTIFIER ::= { cevChassis 182 }
cevChassisUbr10012 OBJECT IDENTIFIER ::= { cevChassis 183 }
cevChassis120168r OBJECT IDENTIFIER ::= { cevChassis 185 }
cevChassis2650  OBJECT IDENTIFIER ::= { cevChassis 186 }
cevChassis2651  OBJECT IDENTIFIER ::= { cevChassis 187 }
cevChassis626   OBJECT IDENTIFIER ::= { cevChassis 196 }
cevChassis627   OBJECT IDENTIFIER ::= { cevChassis 197 }
cevChassis633   OBJECT IDENTIFIER ::= { cevChassis 198 }
cevChassis673   OBJECT IDENTIFIER ::= { cevChassis 199 }
cevChassis675   OBJECT IDENTIFIER ::= { cevChassis 200 }
cevChassis675e  OBJECT IDENTIFIER ::= { cevChassis 201 }
cevChassis676   OBJECT IDENTIFIER ::= { cevChassis 202 }
cevChassis677   OBJECT IDENTIFIER ::= { cevChassis 203 }
cevChassis678   OBJECT IDENTIFIER ::= { cevChassis 204 }
cevChassis3661Ac OBJECT IDENTIFIER ::= { cevChassis 205 }
cevChassis3661Dc OBJECT IDENTIFIER ::= { cevChassis 206 }
cevChassis3662Ac OBJECT IDENTIFIER ::= { cevChassis 207 }
cevChassis3662Dc OBJECT IDENTIFIER ::= { cevChassis 208 }
cevChassis3662AcCo OBJECT IDENTIFIER ::= { cevChassis 209 }
cevChassis3662DcCo OBJECT IDENTIFIER ::= { cevChassis 210 }
cevChassisUbr7111 OBJECT IDENTIFIER ::= { cevChassis 211 }
cevChassisUbr7114 OBJECT IDENTIFIER ::= { cevChassis 213 }
cevChassis12010 OBJECT IDENTIFIER ::= { cevChassis 215 }
cevChassis8110  OBJECT IDENTIFIER ::= { cevChassis 216 }
cevChassis7150Dualfe OBJECT IDENTIFIER ::= { cevChassis 222 }
cevChassis7150Octt1 OBJECT IDENTIFIER ::= { cevChassis 223 }
cevChassis7150Dualt3 OBJECT IDENTIFIER ::= { cevChassis 224 }
cevChassisVPS1110 OBJECT IDENTIFIER ::= { cevChassis 227 }
cevChassisContentEngine OBJECT IDENTIFIER ::= { cevChassis 228 }
cevChassisIAD2420 OBJECT IDENTIFIER ::= { cevChassis 229 }
cevChassis677i  OBJECT IDENTIFIER ::= { cevChassis 230 }
cevChassis674   OBJECT IDENTIFIER ::= { cevChassis 231 }
cevChassisDPA7630 OBJECT IDENTIFIER ::= { cevChassis 232 }
cevChassisCVA122E OBJECT IDENTIFIER ::= { cevChassis 238 }
cevChassisCVA124E OBJECT IDENTIFIER ::= { cevChassis 239 }
cevChassisURM   OBJECT IDENTIFIER ::= { cevChassis 240 }
cevChassisURM2FE OBJECT IDENTIFIER ::= { cevChassis 241 }
cevChassisURM2FE2V OBJECT IDENTIFIER ::= { cevChassis 242 }
cevChassisCAP340 OBJECT IDENTIFIER ::= { cevChassis 245 }
cevChassisDPA7610 OBJECT IDENTIFIER ::= { cevChassis 247 }
cevChassis12416 OBJECT IDENTIFIER ::= { cevChassis 251 }
cevChassisCat2948gL3Dc OBJECT IDENTIFIER ::= { cevChassis 252 }
cevChassisCat4908gL3Dc OBJECT IDENTIFIER ::= { cevChassis 253 }
cevChassis12406 OBJECT IDENTIFIER ::= { cevChassis 254 }
cevChassisPIXFirewall506 OBJECT IDENTIFIER ::= { cevChassis 255 }
cevChassisPIXFirewall515 OBJECT IDENTIFIER ::= { cevChassis 256 }
cevChassisPIXFirewall520 OBJECT IDENTIFIER ::= { cevChassis 257 }
cevChassisPIXFirewall525 OBJECT IDENTIFIER ::= { cevChassis 258 }
cevChassisPIXFirewall535 OBJECT IDENTIFIER ::= { cevChassis 259 }
cevChassis12410 OBJECT IDENTIFIER ::= { cevChassis 260 }
cevChassis811   OBJECT IDENTIFIER ::= { cevChassis 261 }
cevChassis813   OBJECT IDENTIFIER ::= { cevChassis 262 }
cevChassis10720 OBJECT IDENTIFIER ::= { cevChassis 263 }
cevChassis4224  OBJECT IDENTIFIER ::= { cevChassis 265 }
cevChassis7401ASR OBJECT IDENTIFIER ::= { cevChassis 269 }
cevChassis1105  OBJECT IDENTIFIER ::= { cevChassis 271 }
cevChassisONS15540ESP OBJECT IDENTIFIER ::= { cevChassis 272 }
cevChassisCe507 OBJECT IDENTIFIER ::= { cevChassis 275 }
cevChassisCe560 OBJECT IDENTIFIER ::= { cevChassis 276 }
cevChassisCe590 OBJECT IDENTIFIER ::= { cevChassis 277 }
cevChassisCe7320 OBJECT IDENTIFIER ::= { cevChassis 278 }
cevChassisPIXFirewall501 OBJECT IDENTIFIER ::= { cevChassis 283 }
cevChassis2610M OBJECT IDENTIFIER ::= { cevChassis 284 }
cevChassis2611M OBJECT IDENTIFIER ::= { cevChassis 285 }
cevChassis12404 OBJECT IDENTIFIER ::= { cevChassis 289 }
cevChassis9004  OBJECT IDENTIFIER ::= { cevChassis 290 }
cevChassisCE507AV OBJECT IDENTIFIER ::= { cevChassis 298 }
cevChassisCE560AV OBJECT IDENTIFIER ::= { cevChassis 299 }
cevChassisIE2105 OBJECT IDENTIFIER ::= { cevChassis 300 }
cevChassis10005 OBJECT IDENTIFIER ::= { cevChassis 302 }
cevChassis10008 OBJECT IDENTIFIER ::= { cevChassis 303 }
cevChassis7304  OBJECT IDENTIFIER ::= { cevChassis 304 }
cevChassis7505  OBJECT IDENTIFIER ::= { cevChassis 305 }
cevChassisPIXFirewall506E OBJECT IDENTIFIER ::= { cevChassis 317 }
cevChassisPIXFirewall515E OBJECT IDENTIFIER ::= { cevChassis 318 }
cevChassisCe2636 OBJECT IDENTIFIER ::= { cevChassis 320 }
cevChassisCeDw2636 OBJECT IDENTIFIER ::= { cevChassis 321 }
cevChassisONS15530NEBS OBJECT IDENTIFIER ::= { cevChassis 325 }
cevChassisONS15530ETSI OBJECT IDENTIFIER ::= { cevChassis 326 }
cevChassis6400UAC OBJECT IDENTIFIER ::= { cevChassis 328 }
cevChassisRPMPR OBJECT IDENTIFIER ::= { cevChassis 329 }
cevChassis2610XM OBJECT IDENTIFIER ::= { cevChassis 330 }
cevChassis2611XM OBJECT IDENTIFIER ::= { cevChassis 331 }
cevChassis2620XM OBJECT IDENTIFIER ::= { cevChassis 332 }
cevChassis2621XM OBJECT IDENTIFIER ::= { cevChassis 333 }
cevChassis2650XM OBJECT IDENTIFIER ::= { cevChassis 334 }
cevChassis2651XM OBJECT IDENTIFIER ::= { cevChassis 335 }
cevChassisONS15540ESPx OBJECT IDENTIFIER ::= { cevChassis 337 }
cevChassisCat295024sx OBJECT IDENTIFIER ::= { cevChassis 347 }
cevChassisAs5400HPX OBJECT IDENTIFIER ::= { cevChassis 348 }
cevChassis7507  OBJECT IDENTIFIER ::= { cevChassis 363 }
cevChassis7513  OBJECT IDENTIFIER ::= { cevChassis 364 }
cevChassisAIRAP1100 OBJECT IDENTIFIER ::= { cevChassis 365 }
cevChassisDSC9506 OBJECT IDENTIFIER ::= { cevChassis 375 }
cevChassisDSC9509 OBJECT IDENTIFIER ::= { cevChassis 376 }
cevChassisDSC9513 OBJECT IDENTIFIER ::= { cevChassis 377 }
cevChassisONS15201 OBJECT IDENTIFIER ::= { cevChassis 378 }
cevChassisONS15252 OBJECT IDENTIFIER ::= { cevChassis 379 }
cevChassisMdsDSX9216 OBJECT IDENTIFIER ::= { cevChassis 380 }
cevChassisVG200 OBJECT IDENTIFIER ::= { cevChassis 381 }
cevChassisAIRAP1210 OBJECT IDENTIFIER ::= { cevChassis 382 }
cevChassisCe510 OBJECT IDENTIFIER ::= { cevChassis 385 }
cevChassisCe565 OBJECT IDENTIFIER ::= { cevChassis 386 }
cevChassisCe7305 OBJECT IDENTIFIER ::= { cevChassis 387 }
cevChassisCe7325 OBJECT IDENTIFIER ::= { cevChassis 388 }
cevChassisCe4630 OBJECT IDENTIFIER ::= { cevChassis 389 }
cevChassisCe4650 OBJECT IDENTIFIER ::= { cevChassis 390 }
cevBackplane    OBJECT IDENTIFIER ::= { cevMIBObjects 4 }
cevBackplaneAtm OBJECT IDENTIFIER ::= { cevBackplane 4 }
cevBackplaneCat5500 OBJECT IDENTIFIER ::= { cevBackplane 5 }
cevBackplaneCat6400 OBJECT IDENTIFIER ::= { cevBackplane 6 }
cevBackplaneCat8510 OBJECT IDENTIFIER ::= { cevBackplane 7 }
cevBackplaneCat8540 OBJECT IDENTIFIER ::= { cevBackplane 8 }
cevBackplaneMGX8850 OBJECT IDENTIFIER ::= { cevBackplane 9 }
cevBackplaneMGX8820 OBJECT IDENTIFIER ::= { cevBackplane 10 }
cevBackplaneBPXSes OBJECT IDENTIFIER ::= { cevBackplane 11 }
cevBackplaneIGXSes OBJECT IDENTIFIER ::= { cevBackplane 12 }
cevBackplaneCat6000 OBJECT IDENTIFIER ::= { cevBackplane 13 }
cevBackplaneCat6500 OBJECT IDENTIFIER ::= { cevBackplane 14 }
cevBackplaneMGX8950 OBJECT IDENTIFIER ::= { cevBackplane 15 }
cevBackplaneONS15540Fixed OBJECT IDENTIFIER ::= { cevBackplane 16 }
cevBackplaneONS15530 OBJECT IDENTIFIER ::= { cevBackplane 20 }
cevBackplaneDSC9506 OBJECT IDENTIFIER ::= { cevBackplane 26 }
cevBackplaneDSC9509 OBJECT IDENTIFIER ::= { cevBackplane 27 }
cevBackplaneDSC9513 OBJECT IDENTIFIER ::= { cevBackplane 28 }
cevBackplaneONS15540ESPx OBJECT IDENTIFIER ::= { cevBackplane 29 }
cevBackplaneUnknown OBJECT IDENTIFIER ::= { cevBackplane 30 }
cevContainer    OBJECT IDENTIFIER ::= { cevMIBObjects 5 }
cevContainerSlot OBJECT IDENTIFIER ::= { cevContainer 1 }
cevContainerDaughterCard OBJECT IDENTIFIER ::= { cevContainer 2 }
cevContainerPCMCIA OBJECT IDENTIFIER ::= { cevContainer 12 }
cevContainerDSPModuleSlot OBJECT IDENTIFIER ::= { cevContainer 16 }
cevContainerCat8500Carrier OBJECT IDENTIFIER ::= { cevContainer 17 }
cevContainerCat8500CpuSwitchAndFeature OBJECT IDENTIFIER ::= { cevContainer 18 }
cevContainerCat8500CpuSwitchAndFeaturePFQ OBJECT IDENTIFIER ::= { cevContainer 19 }
cevContainerCat8500SuperCarrier OBJECT IDENTIFIER ::= { cevContainer 20 }
cevContainerCat8500CpuRoute OBJECT IDENTIFIER ::= { cevContainer 21 }
cevContainerCat8500Switch10GAndFC OBJECT IDENTIFIER ::= { cevContainer 22 }
cevContainerCat8500Switch10GNoFC OBJECT IDENTIFIER ::= { cevContainer 23 }
cevContainerPsmSlot OBJECT IDENTIFIER ::= { cevContainer 31 }
cevContainerSmSlot OBJECT IDENTIFIER ::= { cevContainer 32 }
cevContainerMGX8800FanTray OBJECT IDENTIFIER ::= { cevContainer 33 }
cevContainerSrmSlot OBJECT IDENTIFIER ::= { cevContainer 34 }
cevContainerMGX8800ACPSTray OBJECT IDENTIFIER ::= { cevContainer 35 }
cevContainerSESFanTray OBJECT IDENTIFIER ::= { cevContainer 36 }
cevContainer12012TopBlowerBay OBJECT IDENTIFIER ::= { cevContainer 37 }
cevContainer12012BottomBlowerBay OBJECT IDENTIFIER ::= { cevContainer 38 }
cevContainer12012ModuleBay OBJECT IDENTIFIER ::= { cevContainer 39 }
cevContainer12012SwitchFabricBay OBJECT IDENTIFIER ::= { cevContainer 40 }
cevContainer12012PowerSupplyBay OBJECT IDENTIFIER ::= { cevContainer 41 }
cevContainer12008PowerBlowerBay OBJECT IDENTIFIER ::= { cevContainer 42 }
cevContainer12008MainBlowerBay OBJECT IDENTIFIER ::= { cevContainer 43 }
cevContainer12008ModuleBay OBJECT IDENTIFIER ::= { cevContainer 44 }
cevContainer12008SwitchFabricBay OBJECT IDENTIFIER ::= { cevContainer 45 }
cevContainer12008PowerSupplyBay OBJECT IDENTIFIER ::= { cevContainer 46 }
cevContainerMGXXm60Slot OBJECT IDENTIFIER ::= { cevContainer 52 }
cevContainerCat8500CMPMCarrier OBJECT IDENTIFIER ::= { cevContainer 55 }
cevContainer12010TopBlowerBay OBJECT IDENTIFIER ::= { cevContainer 56 }
cevContainer12010BottomBlowerBay OBJECT IDENTIFIER ::= { cevContainer 57 }
cevContainer12010UpperModuleBay OBJECT IDENTIFIER ::= { cevContainer 58 }
cevContainer12010LowerModuleBay OBJECT IDENTIFIER ::= { cevContainer 59 }
cevContainer12010SwitchFabricBay OBJECT IDENTIFIER ::= { cevContainer 60 }
cevContainer12010PowerSupplyBay OBJECT IDENTIFIER ::= { cevContainer 61 }
cevContainer12010PowerBlowerBay OBJECT IDENTIFIER ::= { cevContainer 62 }
cevContainer12010MainBlowerBay OBJECT IDENTIFIER ::= { cevContainer 63 }
cevContainer12406ModuleBay OBJECT IDENTIFIER ::= { cevContainer 64 }
cevContainer12406FabricAlarmBay OBJECT IDENTIFIER ::= { cevContainer 65 }
cevContainer12406PowerSupplyBay OBJECT IDENTIFIER ::= { cevContainer 66 }
cevContainer12406MainBlowerBay OBJECT IDENTIFIER ::= { cevContainer 67 }
cevContainer12410TopBlowerBay OBJECT IDENTIFIER ::= { cevContainer 68 }
cevContainer12410BottomBlowerBay OBJECT IDENTIFIER ::= { cevContainer 69 }
cevContainer12410UpperModuleBay OBJECT IDENTIFIER ::= { cevContainer 70 }
cevContainer12410LowerModuleBay OBJECT IDENTIFIER ::= { cevContainer 71 }
cevContainer12410SwitchFabricBay OBJECT IDENTIFIER ::= { cevContainer 72 }
cevContainer12410PowerSupplyBay OBJECT IDENTIFIER ::= { cevContainer 73 }
cevContainer12410PowerBlowerBay OBJECT IDENTIFIER ::= { cevContainer 74 }
cevContainer12410MainBlowerBay OBJECT IDENTIFIER ::= { cevContainer 75 }
cevContainerONS15540CardSlot OBJECT IDENTIFIER ::= { cevContainer 76 }
cevContainerONS15540FanTraySlot OBJECT IDENTIFIER ::= { cevContainer 77 }
cevContainerONS15540TspSubslot OBJECT IDENTIFIER ::= { cevContainer 78 }
cevContainerONS15540MDXSubslot OBJECT IDENTIFIER ::= { cevContainer 79 }
cevContainerONS15540SubCardSlot OBJECT IDENTIFIER ::= { cevContainer 80 }
cevContainer12404ModuleBay OBJECT IDENTIFIER ::= { cevContainer 81 }
cevContainer12404FabricAlarmBay OBJECT IDENTIFIER ::= { cevContainer 82 }
cevContainer12404PowerSupplyBay OBJECT IDENTIFIER ::= { cevContainer 83 }
cevContainer12404MainBlowerBay OBJECT IDENTIFIER ::= { cevContainer 84 }
cevContainerC10KSlot OBJECT IDENTIFIER ::= { cevContainer 86 }
cevContainerC10KPowerSupplySlot OBJECT IDENTIFIER ::= { cevContainer 87 }
cevContainerC10KFanTraySlot OBJECT IDENTIFIER ::= { cevContainer 88 }
cevContainerC10KFlashCardSlot OBJECT IDENTIFIER ::= { cevContainer 89 }
cevContainer12016PowerBlowerBay OBJECT IDENTIFIER ::= { cevContainer 93 }
cevContainer12016LowerModuleBay OBJECT IDENTIFIER ::= { cevContainer 94 }
cevContainer12016SwitchFabricBay OBJECT IDENTIFIER ::= { cevContainer 95 }
cevContainer12016PowerSupplyBay OBJECT IDENTIFIER ::= { cevContainer 96 }
cevContainer12016TopBlowerBay OBJECT IDENTIFIER ::= { cevContainer 97 }
cevContainer12016BottomBlowerBay OBJECT IDENTIFIER ::= { cevContainer 98 }
cevContainer12016UpperModuleBay OBJECT IDENTIFIER ::= { cevContainer 99 }
cevContainerONS15530CardSlot OBJECT IDENTIFIER ::= { cevContainer 100 }
cevContainerONS15530FanTraySlot OBJECT IDENTIFIER ::= { cevContainer 102 }
cevContainerONS15530PSSlot OBJECT IDENTIFIER ::= { cevContainer 103 }
cevContainerONS15530SubCardSlot OBJECT IDENTIFIER ::= { cevContainer 104 }
cevContainerONS15530PortSlot OBJECT IDENTIFIER ::= { cevContainer 105 }
cevContainerONS15540PortSlot OBJECT IDENTIFIER ::= { cevContainer 106 }
cevC10KJacketSlot OBJECT IDENTIFIER ::= { cevContainer 112 }
cevContainerSFP OBJECT IDENTIFIER ::= { cevContainer 115 }
cevContainerGsrAlarmSlot OBJECT IDENTIFIER ::= { cevContainer 116 }
cevContainerGsrPowerSupplySlot OBJECT IDENTIFIER ::= { cevContainer 117 }
cevContainerGsrFanBlowerSlot OBJECT IDENTIFIER ::= { cevContainer 118 }
cevContainerGsrSwitchFabricSlot OBJECT IDENTIFIER ::= { cevContainer 119 }
cevContainerONS15252CardSlot OBJECT IDENTIFIER ::= { cevContainer 120 }
cevContainerONS15201CardSlot OBJECT IDENTIFIER ::= { cevContainer 121 }
cevContainerSupFabricSlot OBJECT IDENTIFIER ::= { cevContainer 122 }
cevContainerLineCardSlot OBJECT IDENTIFIER ::= { cevContainer 123 }
cevContainer9506PowerSupplyBay OBJECT IDENTIFIER ::= { cevContainer 124 }
cevContainer9509PowerSupplyBay OBJECT IDENTIFIER ::= { cevContainer 125 }
cevContainer9513PowerSupplyBay OBJECT IDENTIFIER ::= { cevContainer 126 }
cevContainer9506FanBay OBJECT IDENTIFIER ::= { cevContainer 127 }
cevContainer9509FanBay OBJECT IDENTIFIER ::= { cevContainer 128 }
cevContainer9513FanBay OBJECT IDENTIFIER ::= { cevContainer 129 }
cevContainer9216FanBay OBJECT IDENTIFIER ::= { cevContainer 130 }
cevContainer9216PowerSupplyBay OBJECT IDENTIFIER ::= { cevContainer 131 }
cevContainerC7300CCPA OBJECT IDENTIFIER ::= { cevContainer 132 }
cevPowerSupply  OBJECT IDENTIFIER ::= { cevMIBObjects 6 }
cevPowerSupplyAC1360W OBJECT IDENTIFIER ::= { cevPowerSupply 1 }
cevPowerSupplyDC1360W OBJECT IDENTIFIER ::= { cevPowerSupply 2 }
cevPowerSupplyAC1000W OBJECT IDENTIFIER ::= { cevPowerSupply 3 }
cevPowerSupplyDC1000W OBJECT IDENTIFIER ::= { cevPowerSupply 4 }
cevPowerSupplyPowerone OBJECT IDENTIFIER ::= { cevPowerSupply 5 }
cevPowerSupplyAstec OBJECT IDENTIFIER ::= { cevPowerSupply 6 }
cevPowerSupplyMinus48VDC OBJECT IDENTIFIER ::= { cevPowerSupply 7 }
cevPowerSupplyEmpty OBJECT IDENTIFIER ::= { cevPowerSupply 8 }
cevPowerSupplyAC1100W OBJECT IDENTIFIER ::= { cevPowerSupply 9 }
cevPowerSupplyAC1200W OBJECT IDENTIFIER ::= { cevPowerSupply 10 }
cevPowerSupplyDC1200W OBJECT IDENTIFIER ::= { cevPowerSupply 11 }
cevPowerSupplyPem OBJECT IDENTIFIER ::= { cevPowerSupply 12 }
cevPowerSupplyAC2000W OBJECT IDENTIFIER ::= { cevPowerSupply 13 }
cevPowerSupplyDC2000W OBJECT IDENTIFIER ::= { cevPowerSupply 14 }
cevPowerSupplyMGX8800Pem OBJECT IDENTIFIER ::= { cevPowerSupply 17 }
cevPowerSupply12012DC OBJECT IDENTIFIER ::= { cevPowerSupply 18 }
cevPowerSupply12012AC OBJECT IDENTIFIER ::= { cevPowerSupply 19 }
cevPowerSupply12008DC OBJECT IDENTIFIER ::= { cevPowerSupply 20 }
cevPowerSupply12008AC OBJECT IDENTIFIER ::= { cevPowerSupply 21 }
cevPowerSupplyDC2500W OBJECT IDENTIFIER ::= { cevPowerSupply 22 }
cevPowerSupplyAC1050W OBJECT IDENTIFIER ::= { cevPowerSupply 23 }
cevPowerSupplyAC2500W OBJECT IDENTIFIER ::= { cevPowerSupply 24 }
cevPowerSupply12010DC OBJECT IDENTIFIER ::= { cevPowerSupply 31 }
cevPowerSupply12010AC OBJECT IDENTIFIER ::= { cevPowerSupply 32 }
cevPowerSupply12406DC OBJECT IDENTIFIER ::= { cevPowerSupply 34 }
cevPowerSupply12406AC OBJECT IDENTIFIER ::= { cevPowerSupply 35 }
cevPowerSupply12410DC OBJECT IDENTIFIER ::= { cevPowerSupply 36 }
cevPowerSupply12410AC OBJECT IDENTIFIER ::= { cevPowerSupply 37 }
cevPowerSupply12404DC OBJECT IDENTIFIER ::= { cevPowerSupply 42 }
cevPowerSupply12404AC OBJECT IDENTIFIER ::= { cevPowerSupply 43 }
cevPowerSupplyBP7513AC1200W OBJECT IDENTIFIER ::= { cevPowerSupply 44 }
cevPowerSupplyBP7513DC1200W OBJECT IDENTIFIER ::= { cevPowerSupply 45 }
cevPowerSupplyBP7505AC600W OBJECT IDENTIFIER ::= { cevPowerSupply 46 }
cevPowerSupplyBP7505DC600W OBJECT IDENTIFIER ::= { cevPowerSupply 47 }
cevPowerSupplyBP7507AC700W OBJECT IDENTIFIER ::= { cevPowerSupply 48 }
cevPowerSupplyBP7507DC700W OBJECT IDENTIFIER ::= { cevPowerSupply 49 }
cevPowerSupplyAC600W OBJECT IDENTIFIER ::= { cevPowerSupply 53 }
cevPowerSupplyDC600W OBJECT IDENTIFIER ::= { cevPowerSupply 54 }
cevPowerSupplyC10KDC OBJECT IDENTIFIER ::= { cevPowerSupply 55 }
cevPowerSupplyC10KAC OBJECT IDENTIFIER ::= { cevPowerSupply 56 }
cevPowerSupply15530AC OBJECT IDENTIFIER ::= { cevPowerSupply 59 }
cevPowerSupply15530DC OBJECT IDENTIFIER ::= { cevPowerSupply 60 }
cevPowerSupply12016DC OBJECT IDENTIFIER ::= { cevPowerSupply 63 }
cevPowerSupply12016AC OBJECT IDENTIFIER ::= { cevPowerSupply 64 }
cevPowerSupplyDsCac2500W OBJECT IDENTIFIER ::= { cevPowerSupply 76 }
cevPowerSupplyRedDsCac2500W OBJECT IDENTIFIER ::= { cevPowerSupply 77 }
cevPowerSupplyDsCdc2500W OBJECT IDENTIFIER ::= { cevPowerSupply 78 }
cevPowerSupplyRedDsCdc2500W OBJECT IDENTIFIER ::= { cevPowerSupply 79 }
cevPowerSupplyDsCac4000WUs OBJECT IDENTIFIER ::= { cevPowerSupply 80 }
cevPowerSupplyRedDsCac4000WUs OBJECT IDENTIFIER ::= { cevPowerSupply 81 }
cevPowerSupplyDsCac4000WInt OBJECT IDENTIFIER ::= { cevPowerSupply 82 }
cevPowerSupplyRedDsCac4000WInt OBJECT IDENTIFIER ::= { cevPowerSupply 83 }
cevPowerSupplyDsCac1900W OBJECT IDENTIFIER ::= { cevPowerSupply 84 }
cevPowerSupplyRedDsCac1900W OBJECT IDENTIFIER ::= { cevPowerSupply 85 }
cevPowerSupplyDsCdc1900W OBJECT IDENTIFIER ::= { cevPowerSupply 86 }
cevPowerSupplyRedDsCdc1900W OBJECT IDENTIFIER ::= { cevPowerSupply 87 }
cevPowerSupplyRedDsCac845W OBJECT IDENTIFIER ::= { cevPowerSupply 88 }
cevPowerSupplyDsCac845W OBJECT IDENTIFIER ::= { cevPowerSupply 89 }
cevPowerSupplyUnknown OBJECT IDENTIFIER ::= { cevPowerSupply 90 }
cevPowerSupplyAc150W OBJECT IDENTIFIER ::= { cevPowerSupply 92 }
cevFan          OBJECT IDENTIFIER ::= { cevMIBObjects 7 }
cevFanSinglePulse OBJECT IDENTIFIER ::= { cevFan 4 }
cevFanDualPulse OBJECT IDENTIFIER ::= { cevFan 5 }
cevFan12012FanTray3 OBJECT IDENTIFIER ::= { cevFan 6 }
cevFan12008FanTray6 OBJECT IDENTIFIER ::= { cevFan 7 }
cevFan12008FanTray4 OBJECT IDENTIFIER ::= { cevFan 8 }
cevFanC6100FanTray OBJECT IDENTIFIER ::= { cevFan 11 }
cevFan12010FanTray3 OBJECT IDENTIFIER ::= { cevFan 13 }
cevFan12406FanTray3 OBJECT IDENTIFIER ::= { cevFan 14 }
cevFan12410FanTray3 OBJECT IDENTIFIER ::= { cevFan 15 }
cevFanONS15540FanTray8 OBJECT IDENTIFIER ::= { cevFan 16 }
cevFan12404FanTray7 OBJECT IDENTIFIER ::= { cevFan 17 }
cevFanBP7513MainFan OBJECT IDENTIFIER ::= { cevFan 18 }
cevFanBP7513PS1Fan OBJECT IDENTIFIER ::= { cevFan 19 }
cevFanBP7513PS2Fan OBJECT IDENTIFIER ::= { cevFan 20 }
cevFan7505Fan   OBJECT IDENTIFIER ::= { cevFan 21 }
cevFan7507Fan   OBJECT IDENTIFIER ::= { cevFan 22 }
cevFanTrayC10008 OBJECT IDENTIFIER ::= { cevFan 25 }
cevFanTrayC10005 OBJECT IDENTIFIER ::= { cevFan 26 }
cevFanC6160ITempFanTray OBJECT IDENTIFIER ::= { cevFan 29 }
cevFanONS15530FanTray6 OBJECT IDENTIFIER ::= { cevFan 30 }
cevFan12016FanTray3 OBJECT IDENTIFIER ::= { cevFan 31 }
cevFanDs6SlotFanTray OBJECT IDENTIFIER ::= { cevFan 35 }
cevFanDSC9509FanTray OBJECT IDENTIFIER ::= { cevFan 36 }
cevFanDSC9513FanTray OBJECT IDENTIFIER ::= { cevFan 37 }
cevFanTrayUnknown OBJECT IDENTIFIER ::= { cevFan 38 }
cevFanDsX9216FanTray OBJECT IDENTIFIER ::= { cevFan 39 }
cevFanCat3710CFM26 OBJECT IDENTIFIER ::= { cevFan 40 }
cevSensor       OBJECT IDENTIFIER ::= { cevMIBObjects 8 }
cevSensorMGX8800Temp OBJECT IDENTIFIER ::= { cevSensor 11 }
cevSensorMGX8800PSVoltage OBJECT IDENTIFIER ::= { cevSensor 12 }
cevSensorMGX8800FanSpeed OBJECT IDENTIFIER ::= { cevSensor 13 }
cevSensorONS15540Temp OBJECT IDENTIFIER ::= { cevSensor 14 }
cevSensorONS15540Power OBJECT IDENTIFIER ::= { cevSensor 15 }
cevSensor7500ChassisInterface OBJECT IDENTIFIER ::= { cevSensor 16 }
cevSensorC10KInletTemp OBJECT IDENTIFIER ::= { cevSensor 22 }
cevSensorC10000CoreTemp OBJECT IDENTIFIER ::= { cevSensor 23 }
cevSensorONS15530Temp OBJECT IDENTIFIER ::= { cevSensor 25 }
cevSensorONS15530Power OBJECT IDENTIFIER ::= { cevSensor 26 }
cevSensor15302701Temp OBJECT IDENTIFIER ::= { cevSensor 29 }
cevSensorUnknown OBJECT IDENTIFIER ::= { cevSensor 30 }
cevModule       OBJECT IDENTIFIER ::= { cevMIBObjects 9 }
cevModuleUnknownCard OBJECT IDENTIFIER ::= { cevModule 1 }
cevModuleCommonCards OBJECT IDENTIFIER ::= { cevModule 2 }
cevWicSerial1t  OBJECT IDENTIFIER ::= { cevModuleCommonCards 1 }
cevWicST3420    OBJECT IDENTIFIER ::= { cevModuleCommonCards 5 }
cevWicST2186    OBJECT IDENTIFIER ::= { cevModuleCommonCards 6 }
cevWicU3420     OBJECT IDENTIFIER ::= { cevModuleCommonCards 7 }
cevWicU2091     OBJECT IDENTIFIER ::= { cevModuleCommonCards 8 }
cevWicU20912081 OBJECT IDENTIFIER ::= { cevModuleCommonCards 9 }
cevWicST2186Leased OBJECT IDENTIFIER ::= { cevModuleCommonCards 10 }
cevVicFxs       OBJECT IDENTIFIER ::= { cevModuleCommonCards 11 }
cevVicFxo       OBJECT IDENTIFIER ::= { cevModuleCommonCards 12 }
cevVicEm        OBJECT IDENTIFIER ::= { cevModuleCommonCards 13 }
cevAimCompression OBJECT IDENTIFIER ::= { cevModuleCommonCards 14 }
cevWicSerial2as OBJECT IDENTIFIER ::= { cevModuleCommonCards 29 }
cevWicCsuDsuFT1 OBJECT IDENTIFIER ::= { cevModuleCommonCards 30 }
cevIsaIpsecMppe OBJECT IDENTIFIER ::= { cevModuleCommonCards 31 }
cevWicDslsar20150 OBJECT IDENTIFIER ::= { cevModuleCommonCards 32 }
cevWicSerial1t12in1 OBJECT IDENTIFIER ::= { cevModuleCommonCards 44 }
cevVic4vpFxsDid OBJECT IDENTIFIER ::= { cevModuleCommonCards 49 }
cevVic4fxoUsM1  OBJECT IDENTIFIER ::= { cevModuleCommonCards 50 }
cevVic4fxoM2M3  OBJECT IDENTIFIER ::= { cevModuleCommonCards 51 }
cevVic4fxoCAMA  OBJECT IDENTIFIER ::= { cevModuleCommonCards 52 }
cevWicEthernet  OBJECT IDENTIFIER ::= { cevModuleCommonCards 55 }
cevCeSA6DC      OBJECT IDENTIFIER ::= { cevModuleCommonCards 56 }
cevCeSA6AC      OBJECT IDENTIFIER ::= { cevModuleCommonCards 57 }
cevCeSA12AC     OBJECT IDENTIFIER ::= { cevModuleCommonCards 58 }
cevC2610XM1Fe   OBJECT IDENTIFIER ::= { cevModuleCommonCards 59 }
cevC2611XM2Fe   OBJECT IDENTIFIER ::= { cevModuleCommonCards 60 }
cevC2620XM1Fe   OBJECT IDENTIFIER ::= { cevModuleCommonCards 61 }
cevC2621XM2Fe   OBJECT IDENTIFIER ::= { cevModuleCommonCards 62 }
cevC2650XM1Fe   OBJECT IDENTIFIER ::= { cevModuleCommonCards 63 }
cevC2651XM2Fe   OBJECT IDENTIFIER ::= { cevModuleCommonCards 64 }
cevCeSA14       OBJECT IDENTIFIER ::= { cevModuleCommonCards 66 }
cevIpSecSWVPA   OBJECT IDENTIFIER ::= { cevModuleCommonCards 69 }
cevNmSe         OBJECT IDENTIFIER ::= { cevModuleCommonCards 70 }
cevAimSe        OBJECT IDENTIFIER ::= { cevModuleCommonCards 71 }
cevWicSe        OBJECT IDENTIFIER ::= { cevModuleCommonCards 72 }
cevCeDs2100     OBJECT IDENTIFIER ::= { cevModuleCommonCards 73 }
cevOc3Atm2Vpa   OBJECT IDENTIFIER ::= { cevModuleCommonCards 76 }
cevOc3Atm4Vpa   OBJECT IDENTIFIER ::= { cevModuleCommonCards 77 }
cevOc12Atm1Vpa  OBJECT IDENTIFIER ::= { cevModuleCommonCards 78 }
cevOc12Atm2Vpa  OBJECT IDENTIFIER ::= { cevModuleCommonCards 79 }
cevOc48Atm1Vpa  OBJECT IDENTIFIER ::= { cevModuleCommonCards 80 }
cevT3e3Atm2Vpa  OBJECT IDENTIFIER ::= { cevModuleCommonCards 81 }
cevT3e3Atm4Vpa  OBJECT IDENTIFIER ::= { cevModuleCommonCards 82 }
cevModuleC36xxType OBJECT IDENTIFIER ::= { cevModule 3 }
cevPmCpm1e2w    OBJECT IDENTIFIER ::= { cevModuleC36xxType 1 }
cevPmCpm2e2w    OBJECT IDENTIFIER ::= { cevModuleC36xxType 2 }
cevPmCpm1e1r2w  OBJECT IDENTIFIER ::= { cevModuleC36xxType 3 }
cevPmCt1Csu     OBJECT IDENTIFIER ::= { cevModuleC36xxType 4 }
cevPm2ct1Csu    OBJECT IDENTIFIER ::= { cevModuleC36xxType 5 }
cevPmCt1Dsx1    OBJECT IDENTIFIER ::= { cevModuleC36xxType 6 }
cevPm2ct1Dsx1   OBJECT IDENTIFIER ::= { cevModuleC36xxType 7 }
cevPmCe1Balanced OBJECT IDENTIFIER ::= { cevModuleC36xxType 8 }
cevPm2ce1Balanced OBJECT IDENTIFIER ::= { cevModuleC36xxType 9 }
cevPmCe1Unbalanced OBJECT IDENTIFIER ::= { cevModuleC36xxType 10 }
cevPm2ce1Unbalanced OBJECT IDENTIFIER ::= { cevModuleC36xxType 11 }
cevPm4bU        OBJECT IDENTIFIER ::= { cevModuleC36xxType 12 }
cevPm4bSt       OBJECT IDENTIFIER ::= { cevModuleC36xxType 13 }
cevPm8bU        OBJECT IDENTIFIER ::= { cevModuleC36xxType 14 }
cevPm8bSt       OBJECT IDENTIFIER ::= { cevModuleC36xxType 15 }
cevPm4as        OBJECT IDENTIFIER ::= { cevModuleC36xxType 16 }
cevPm8as        OBJECT IDENTIFIER ::= { cevModuleC36xxType 17 }
cevPm4e         OBJECT IDENTIFIER ::= { cevModuleC36xxType 18 }
cevPm1e         OBJECT IDENTIFIER ::= { cevModuleC36xxType 19 }
cevPmM4t        OBJECT IDENTIFIER ::= { cevModuleC36xxType 21 }
cevPm16a        OBJECT IDENTIFIER ::= { cevModuleC36xxType 22 }
cevPm32a        OBJECT IDENTIFIER ::= { cevModuleC36xxType 23 }
cevPmC36001fe   OBJECT IDENTIFIER ::= { cevModuleC36xxType 24 }
cevPmC3600Compression OBJECT IDENTIFIER ::= { cevModuleC36xxType 25 }
cevPmDmodem     OBJECT IDENTIFIER ::= { cevModuleC36xxType 26 }
cevPm8admodem   OBJECT IDENTIFIER ::= { cevModuleC36xxType 27 }
cevPm16admodem  OBJECT IDENTIFIER ::= { cevModuleC36xxType 28 }
cevVpm2v        OBJECT IDENTIFIER ::= { cevModuleC36xxType 29 }
cevVpm4v        OBJECT IDENTIFIER ::= { cevModuleC36xxType 30 }
cevPmC36001feTx OBJECT IDENTIFIER ::= { cevModuleC36xxType 31 }
cevPmC36001feFx OBJECT IDENTIFIER ::= { cevModuleC36xxType 32 }
cevPm1fe1t1     OBJECT IDENTIFIER ::= { cevModuleC36xxType 33 }
cevPm1fe2t1     OBJECT IDENTIFIER ::= { cevModuleC36xxType 34 }
cevPm1fe1e1     OBJECT IDENTIFIER ::= { cevModuleC36xxType 35 }
cevPm1fe2e1     OBJECT IDENTIFIER ::= { cevModuleC36xxType 36 }
cevPm1fe1t1Csu  OBJECT IDENTIFIER ::= { cevModuleC36xxType 37 }
cevPm1fe2t1Csu  OBJECT IDENTIFIER ::= { cevModuleC36xxType 38 }
cevC36xx2feTx   OBJECT IDENTIFIER ::= { cevModuleC36xxType 39 }
cevPmOc3mm      OBJECT IDENTIFIER ::= { cevModuleC36xxType 40 }
cevPmOc3mmVpd   OBJECT IDENTIFIER ::= { cevModuleC36xxType 41 }
cevPmOc3smiVpd  OBJECT IDENTIFIER ::= { cevModuleC36xxType 42 }
cevPmOc3smlVpd  OBJECT IDENTIFIER ::= { cevModuleC36xxType 43 }
cevPmOc3sml     OBJECT IDENTIFIER ::= { cevModuleC36xxType 44 }
cevPmOc3smi     OBJECT IDENTIFIER ::= { cevModuleC36xxType 45 }
cevVic2fxoEu    OBJECT IDENTIFIER ::= { cevModuleC36xxType 46 }
cevVic2fxoM3    OBJECT IDENTIFIER ::= { cevModuleC36xxType 47 }
cevVic2fxoM4    OBJECT IDENTIFIER ::= { cevModuleC36xxType 48 }
cevVic2fxoM5    OBJECT IDENTIFIER ::= { cevModuleC36xxType 49 }
cevVic2fxoM6    OBJECT IDENTIFIER ::= { cevModuleC36xxType 50 }
cevVic2fxoM7    OBJECT IDENTIFIER ::= { cevModuleC36xxType 51 }
cevVic2fxoM8    OBJECT IDENTIFIER ::= { cevModuleC36xxType 52 }
cevVic2ST2086   OBJECT IDENTIFIER ::= { cevModuleC36xxType 53 }
cevHdv          OBJECT IDENTIFIER ::= { cevModuleC36xxType 54 }
cevNm1fe2w      OBJECT IDENTIFIER ::= { cevModuleC36xxType 59 }
cevNm2fe2w      OBJECT IDENTIFIER ::= { cevModuleC36xxType 60 }
cevNm1fe1r2w    OBJECT IDENTIFIER ::= { cevModuleC36xxType 61 }
cevNm2w         OBJECT IDENTIFIER ::= { cevModuleC36xxType 62 }
cevC36xx1feTx   OBJECT IDENTIFIER ::= { cevModuleC36xxType 63 }
cevAimLc4e1Compression OBJECT IDENTIFIER ::= { cevModuleC36xxType 64 }
cevVic2fxoM2    OBJECT IDENTIFIER ::= { cevModuleC36xxType 68 }
cevPmDs3        OBJECT IDENTIFIER ::= { cevModuleC36xxType 69 }
cevPmE3         OBJECT IDENTIFIER ::= { cevModuleC36xxType 70 }
cevVic2vpFxsDid OBJECT IDENTIFIER ::= { cevModuleC36xxType 74 }
cevVic2ST2086NtTe OBJECT IDENTIFIER ::= { cevModuleC36xxType 75 }
cevNmAic64      OBJECT IDENTIFIER ::= { cevModuleC36xxType 76 }
cevMIX366064    OBJECT IDENTIFIER ::= { cevModuleC36xxType 77 }
cevWicAsync1am  OBJECT IDENTIFIER ::= { cevModuleC36xxType 78 }
cevWicAsync2am  OBJECT IDENTIFIER ::= { cevModuleC36xxType 79 }
cevHdv4fxs      OBJECT IDENTIFIER ::= { cevModuleC36xxType 82 }
cevC2610M       OBJECT IDENTIFIER ::= { cevModuleC36xxType 84 }
cevC2611M       OBJECT IDENTIFIER ::= { cevModuleC36xxType 85 }
cevNm1t3e3      OBJECT IDENTIFIER ::= { cevModuleC36xxType 91 }
cevNm1ct3e3     OBJECT IDENTIFIER ::= { cevModuleC36xxType 92 }
cevNm8ct1e1     OBJECT IDENTIFIER ::= { cevModuleC36xxType 93 }
cevHdaEm4fxo    OBJECT IDENTIFIER ::= { cevModuleC36xxType 94 }
cevModuleVipPortAdapters OBJECT IDENTIFIER ::= { cevModule 4 }
cevPa1fe        OBJECT IDENTIFIER ::= { cevModuleVipPortAdapters 1 }
cevPa8e         OBJECT IDENTIFIER ::= { cevModuleVipPortAdapters 2 }
cevPa4e         OBJECT IDENTIFIER ::= { cevModuleVipPortAdapters 3 }
cevPa5e         OBJECT IDENTIFIER ::= { cevModuleVipPortAdapters 4 }
cevPa4t         OBJECT IDENTIFIER ::= { cevModuleVipPortAdapters 5 }
cevPa4r         OBJECT IDENTIFIER ::= { cevModuleVipPortAdapters 6 }
cevPaFddi       OBJECT IDENTIFIER ::= { cevModuleVipPortAdapters 7 }
cevSaEncryption OBJECT IDENTIFIER ::= { cevModuleVipPortAdapters 8 }
cevPaAh1t       OBJECT IDENTIFIER ::= { cevModuleVipPortAdapters 9 }
cevPaAh2t       OBJECT IDENTIFIER ::= { cevModuleVipPortAdapters 10 }
cevPaA8tV35     OBJECT IDENTIFIER ::= { cevModuleVipPortAdapters 12 }
cevPa1feTxIsl   OBJECT IDENTIFIER ::= { cevModuleVipPortAdapters 13 }
cevPa1feFxIsl   OBJECT IDENTIFIER ::= { cevModuleVipPortAdapters 14 }
cevPa1feTxNisl  OBJECT IDENTIFIER ::= { cevModuleVipPortAdapters 15 }
cevSaCompression OBJECT IDENTIFIER ::= { cevModuleVipPortAdapters 16 }
cevPaAtmLite1   OBJECT IDENTIFIER ::= { cevModuleVipPortAdapters 17 }
cevPaCt3        OBJECT IDENTIFIER ::= { cevModuleVipPortAdapters 18 }
cevPaOc3smMuxCbrt1 OBJECT IDENTIFIER ::= { cevModuleVipPortAdapters 19 }
cevPaOc3smMuxCbr120e1 OBJECT IDENTIFIER ::= { cevModuleVipPortAdapters 20 }
cevPaOc3smMuxCbr75e1 OBJECT IDENTIFIER ::= { cevModuleVipPortAdapters 21 }
cevPaOc3mmMuxCbrt1 OBJECT IDENTIFIER ::= { cevModuleVipPortAdapters 22 }
cevPaOc3mmMuxCbr120e1 OBJECT IDENTIFIER ::= { cevModuleVipPortAdapters 23 }
cevPaOc3mmMuxCbr75e1 OBJECT IDENTIFIER ::= { cevModuleVipPortAdapters 24 }
cevPaDs3MuxCbrt1 OBJECT IDENTIFIER ::= { cevModuleVipPortAdapters 25 }
cevPaE3MuxCbr120e1 OBJECT IDENTIFIER ::= { cevModuleVipPortAdapters 26 }
cevPaE3smMuxCbr75e1 OBJECT IDENTIFIER ::= { cevModuleVipPortAdapters 27 }
cevPa8bSt       OBJECT IDENTIFIER ::= { cevModuleVipPortAdapters 28 }
cevPa4bU        OBJECT IDENTIFIER ::= { cevModuleVipPortAdapters 29 }
cevPaFddiFd     OBJECT IDENTIFIER ::= { cevModuleVipPortAdapters 30 }
cevPaJt2        OBJECT IDENTIFIER ::= { cevModuleVipPortAdapters 31 }
cevPaPosdw      OBJECT IDENTIFIER ::= { cevModuleVipPortAdapters 32 }
cevPa4me1Bal    OBJECT IDENTIFIER ::= { cevModuleVipPortAdapters 33 }
cevPa2ce1Balanced OBJECT IDENTIFIER ::= { cevModuleVipPortAdapters 34 }
cevPa2ct1       OBJECT IDENTIFIER ::= { cevModuleVipPortAdapters 35 }
cevPa1vg        OBJECT IDENTIFIER ::= { cevModuleVipPortAdapters 36 }
cevPaAtmdxDs3   OBJECT IDENTIFIER ::= { cevModuleVipPortAdapters 37 }
cevPaAtmdxE3    OBJECT IDENTIFIER ::= { cevModuleVipPortAdapters 38 }
cevPaAtmdxSmlOc3 OBJECT IDENTIFIER ::= { cevModuleVipPortAdapters 39 }
cevPaAtmdxSmiOc3 OBJECT IDENTIFIER ::= { cevModuleVipPortAdapters 40 }
cevPaAtmdxMmOc3 OBJECT IDENTIFIER ::= { cevModuleVipPortAdapters 41 }
cevPaA8tX21     OBJECT IDENTIFIER ::= { cevModuleVipPortAdapters 42 }
cevPaA8tRs232   OBJECT IDENTIFIER ::= { cevModuleVipPortAdapters 43 }
cevPa4me1Unbal  OBJECT IDENTIFIER ::= { cevModuleVipPortAdapters 44 }
cevPa4rFdx      OBJECT IDENTIFIER ::= { cevModuleVipPortAdapters 45 }
cevPa1e3        OBJECT IDENTIFIER ::= { cevModuleVipPortAdapters 46 }
cevPa2e3        OBJECT IDENTIFIER ::= { cevModuleVipPortAdapters 47 }
cevPa1t3        OBJECT IDENTIFIER ::= { cevModuleVipPortAdapters 48 }
cevPa2t3        OBJECT IDENTIFIER ::= { cevModuleVipPortAdapters 49 }
cevPa2ce1Unbalanced OBJECT IDENTIFIER ::= { cevModuleVipPortAdapters 50 }
cevPa14eSwitch  OBJECT IDENTIFIER ::= { cevModuleVipPortAdapters 51 }
cevas58001fedsi OBJECT IDENTIFIER ::= { cevModuleVipPortAdapters 52 }
cevPa1feFxNisl  OBJECT IDENTIFIER ::= { cevModuleVipPortAdapters 53 }
cevPaIo1fe      OBJECT IDENTIFIER ::= { cevModuleVipPortAdapters 54 }
cevPaIo         OBJECT IDENTIFIER ::= { cevModuleVipPortAdapters 55 }
cevPa2feTx      OBJECT IDENTIFIER ::= { cevModuleVipPortAdapters 56 }
cevPa2feFx      OBJECT IDENTIFIER ::= { cevModuleVipPortAdapters 57 }
cevPaGe         OBJECT IDENTIFIER ::= { cevModuleVipPortAdapters 59 }
cevPaPosswSm    OBJECT IDENTIFIER ::= { cevModuleVipPortAdapters 60 }
cevPaPosswMm    OBJECT IDENTIFIER ::= { cevModuleVipPortAdapters 61 }
cevPaPosswLr    OBJECT IDENTIFIER ::= { cevModuleVipPortAdapters 62 }
cevPa4ct1Csu    OBJECT IDENTIFIER ::= { cevModuleVipPortAdapters 63 }
cevPa8ct1Csu    OBJECT IDENTIFIER ::= { cevModuleVipPortAdapters 64 }
cevPa8ct1       OBJECT IDENTIFIER ::= { cevModuleVipPortAdapters 65 }
cevPa8ce1       OBJECT IDENTIFIER ::= { cevModuleVipPortAdapters 66 }
cevPaAtmOc12Mm  OBJECT IDENTIFIER ::= { cevModuleVipPortAdapters 69 }
cevPaAtmOc12Smi OBJECT IDENTIFIER ::= { cevModuleVipPortAdapters 70 }
cevPaMct3       OBJECT IDENTIFIER ::= { cevModuleVipPortAdapters 71 }
cevPaMc2t3      OBJECT IDENTIFIER ::= { cevModuleVipPortAdapters 72 }
cevPa1t3Plus    OBJECT IDENTIFIER ::= { cevModuleVipPortAdapters 73 }
cevPa2t3Plus    OBJECT IDENTIFIER ::= { cevModuleVipPortAdapters 74 }
cevPaPosOc12Mm  OBJECT IDENTIFIER ::= { cevModuleVipPortAdapters 75 }
cevPaPosOc12Sm  OBJECT IDENTIFIER ::= { cevModuleVipPortAdapters 76 }
cevPaImaT1      OBJECT IDENTIFIER ::= { cevModuleVipPortAdapters 77 }
cevPaImaE1      OBJECT IDENTIFIER ::= { cevModuleVipPortAdapters 78 }
cevSrpPaOc12Mm  OBJECT IDENTIFIER ::= { cevModuleVipPortAdapters 79 }
cevSrpPaOc12SmIr OBJECT IDENTIFIER ::= { cevModuleVipPortAdapters 80 }
cevSrpPaOc12Lr  OBJECT IDENTIFIER ::= { cevModuleVipPortAdapters 81 }
cevPa2ct1Csu    OBJECT IDENTIFIER ::= { cevModuleVipPortAdapters 82 }
cevPa2ce1       OBJECT IDENTIFIER ::= { cevModuleVipPortAdapters 83 }
cevPaMcx2te1    OBJECT IDENTIFIER ::= { cevModuleVipPortAdapters 84 }
cevPaMcx4te1    OBJECT IDENTIFIER ::= { cevModuleVipPortAdapters 85 }
cevPaMcx8te1    OBJECT IDENTIFIER ::= { cevModuleVipPortAdapters 86 }
cevSrpPaOc12SmXr OBJECT IDENTIFIER ::= { cevModuleVipPortAdapters 87 }
cevPa2feTxI82543 OBJECT IDENTIFIER ::= { cevModuleVipPortAdapters 92 }
cevPa2feFxI82543 OBJECT IDENTIFIER ::= { cevModuleVipPortAdapters 93 }
cevPaDualWideGe OBJECT IDENTIFIER ::= { cevModuleVipPortAdapters 94 }
cevPaVxa1T1E124 OBJECT IDENTIFIER ::= { cevModuleVipPortAdapters 95 }
cevPaVxa1T1E130 OBJECT IDENTIFIER ::= { cevModuleVipPortAdapters 96 }
cevPaMcT1E1     OBJECT IDENTIFIER ::= { cevModuleVipPortAdapters 97 }
cevPaMcx8te1M   OBJECT IDENTIFIER ::= { cevModuleVipPortAdapters 99 }
cevPa1ce3       OBJECT IDENTIFIER ::= { cevModuleVipPortAdapters 100 }
cevPa2OC3PosSw  OBJECT IDENTIFIER ::= { cevModuleVipPortAdapters 101 }
cevModuleCpuType OBJECT IDENTIFIER ::= { cevModule 5 }
cevC7200Io1fe   OBJECT IDENTIFIER ::= { cevModuleCpuType 1 }
cevC7200Io      OBJECT IDENTIFIER ::= { cevModuleCpuType 2 }
cevCpuAS5300    OBJECT IDENTIFIER ::= { cevModuleCpuType 3 }
cevCpuRpm       OBJECT IDENTIFIER ::= { cevModuleCpuType 7 }
cevCpu2600      OBJECT IDENTIFIER ::= { cevModuleCpuType 8 }
cevCpu7200Npe300 OBJECT IDENTIFIER ::= { cevModuleCpuType 9 }
cevCpu1400      OBJECT IDENTIFIER ::= { cevModuleCpuType 10 }
cevCpu800       OBJECT IDENTIFIER ::= { cevModuleCpuType 11 }
cevCpuPSM1Gbps  OBJECT IDENTIFIER ::= { cevModuleCpuType 12 }
cevCpu7200Npe175 OBJECT IDENTIFIER ::= { cevModuleCpuType 14 }
cevCpu7200Npe225 OBJECT IDENTIFIER ::= { cevModuleCpuType 15 }
cevCpu1417      OBJECT IDENTIFIER ::= { cevModuleCpuType 17 }
cevCpuPsm11oc12 OBJECT IDENTIFIER ::= { cevModuleCpuType 18 }
cevCpuOpticalRegenerator OBJECT IDENTIFIER ::= { cevModuleCpuType 19 }
cevCpuUbr924    OBJECT IDENTIFIER ::= { cevModuleCpuType 20 }
cevCpu7120      OBJECT IDENTIFIER ::= { cevModuleCpuType 21 }
cevCpu7140      OBJECT IDENTIFIER ::= { cevModuleCpuType 22 }
cevCpuPsm12t3e3 OBJECT IDENTIFIER ::= { cevModuleCpuType 23 }
cevCpuPsm14oc3  OBJECT IDENTIFIER ::= { cevModuleCpuType 24 }
cevCpu7200Npe100 OBJECT IDENTIFIER ::= { cevModuleCpuType 26 }
cevCpu7200Npe150 OBJECT IDENTIFIER ::= { cevModuleCpuType 27 }
cevCpu7200Npe200 OBJECT IDENTIFIER ::= { cevModuleCpuType 28 }
cevCpuCreRp     OBJECT IDENTIFIER ::= { cevModuleCpuType 29 }
cevCpuCreFp     OBJECT IDENTIFIER ::= { cevModuleCpuType 30 }
cevCpuAS5200    OBJECT IDENTIFIER ::= { cevModuleCpuType 34 }
cevCpuGrp       OBJECT IDENTIFIER ::= { cevModuleCpuType 35 }
cevCpuMc3810V3  OBJECT IDENTIFIER ::= { cevModuleCpuType 36 }
cevCpuUbr91x    OBJECT IDENTIFIER ::= { cevModuleCpuType 42 }
cevCpu7150      OBJECT IDENTIFIER ::= { cevModuleCpuType 43 }
cevCpuPXMB45Gbps OBJECT IDENTIFIER ::= { cevModuleCpuType 44 }
cevCpuONS15540  OBJECT IDENTIFIER ::= { cevModuleCpuType 47 }
cevCpuPrp1      OBJECT IDENTIFIER ::= { cevModuleCpuType 49 }
cevCpu7200Npeg1 OBJECT IDENTIFIER ::= { cevModuleCpuType 56 }
cevCpuONS15530SW OBJECT IDENTIFIER ::= { cevModuleCpuType 62 }
cevCpu6400Nsp   OBJECT IDENTIFIER ::= { cevModuleCpuType 63 }
cevCpu6400Nrp   OBJECT IDENTIFIER ::= { cevModuleCpuType 64 }
cevCpu6400Nrp2  OBJECT IDENTIFIER ::= { cevModuleCpuType 65 }
cevCpu6400Nrp2Sv OBJECT IDENTIFIER ::= { cevModuleCpuType 66 }
cevCpu1700      OBJECT IDENTIFIER ::= { cevModuleCpuType 68 }
cevCpu4604      OBJECT IDENTIFIER ::= { cevModuleCpuType 75 }
cevCpu4224      OBJECT IDENTIFIER ::= { cevModuleCpuType 76 }
cevCpuAs5400HPX OBJECT IDENTIFIER ::= { cevModuleCpuType 77 }
cevCpuMdsCpp    OBJECT IDENTIFIER ::= { cevModuleCpuType 82 }
cevCpuMdsDpp    OBJECT IDENTIFIER ::= { cevModuleCpuType 83 }
cevCpuMdsSup    OBJECT IDENTIFIER ::= { cevModuleCpuType 84 }
cevModuleCscType OBJECT IDENTIFIER ::= { cevModule 6 }
cevModuleC7xxxType OBJECT IDENTIFIER ::= { cevModule 7 }
cevC7xxxMc14a   OBJECT IDENTIFIER ::= { cevModuleC7xxxType 1 }
cevC7xxxMc16a   OBJECT IDENTIFIER ::= { cevModuleC7xxxType 2 }
cevC7xxxMc11    OBJECT IDENTIFIER ::= { cevModuleC7xxxType 3 }
cevC7xxxMc12a   OBJECT IDENTIFIER ::= { cevModuleC7xxxType 4 }
cevC7xxxMc11a   OBJECT IDENTIFIER ::= { cevModuleC7xxxType 5 }
cevC7xxxIo1feTxIsl OBJECT IDENTIFIER ::= { cevModuleC7xxxType 6 }
cevC7xxxMc28    OBJECT IDENTIFIER ::= { cevModuleC7xxxType 8 }
cevVip480       OBJECT IDENTIFIER ::= { cevModuleC7xxxType 9 }
cevVip450       OBJECT IDENTIFIER ::= { cevModuleC7xxxType 10 }
cevC7xxxIoEGE   OBJECT IDENTIFIER ::= { cevModuleC7xxxType 11 }
cevC7xxxIo2FE   OBJECT IDENTIFIER ::= { cevModuleC7xxxType 12 }
cevC7xxxEIP     OBJECT IDENTIFIER ::= { cevModuleC7xxxType 16 }
cevC7xxxFIP     OBJECT IDENTIFIER ::= { cevModuleC7xxxType 17 }
cevC7xxxSrsFIP  OBJECT IDENTIFIER ::= { cevModuleC7xxxType 18 }
cevC7xxxTRIP    OBJECT IDENTIFIER ::= { cevModuleC7xxxType 19 }
cevC7xxxSrsTRIP OBJECT IDENTIFIER ::= { cevModuleC7xxxType 20 }
cevC7xxxFSIP    OBJECT IDENTIFIER ::= { cevModuleC7xxxType 21 }
cevC7xxxSSIP    OBJECT IDENTIFIER ::= { cevModuleC7xxxType 22 }
cevC7xxxMIP     OBJECT IDENTIFIER ::= { cevModuleC7xxxType 23 }
cevC7xxxSMIP    OBJECT IDENTIFIER ::= { cevModuleC7xxxType 24 }
cevC7xxxVIP2    OBJECT IDENTIFIER ::= { cevModuleC7xxxType 25 }
cevC7xxxVIP250  OBJECT IDENTIFIER ::= { cevModuleC7xxxType 26 }
cevC7xxxRSP1    OBJECT IDENTIFIER ::= { cevModuleC7xxxType 27 }
cevC7xxxRSP2    OBJECT IDENTIFIER ::= { cevModuleC7xxxType 28 }
cevC7xxxRSP4    OBJECT IDENTIFIER ::= { cevModuleC7xxxType 29 }
cevC7xxxPosIP   OBJECT IDENTIFIER ::= { cevModuleC7xxxType 30 }
cevC7xxxFeIP2   OBJECT IDENTIFIER ::= { cevModuleC7xxxType 31 }
cevC73004Oc3PosMm OBJECT IDENTIFIER ::= { cevModuleC7xxxType 33 }
cevC73004Oc3PosSmIr OBJECT IDENTIFIER ::= { cevModuleC7xxxType 34 }
cevC73004Oc3PosSmLr OBJECT IDENTIFIER ::= { cevModuleC7xxxType 35 }
cevC7300Oc48PosSmSr OBJECT IDENTIFIER ::= { cevModuleC7xxxType 36 }
cevC7300Oc48PosSmIr OBJECT IDENTIFIER ::= { cevModuleC7xxxType 37 }
cevC7300Oc48PosSmLr OBJECT IDENTIFIER ::= { cevModuleC7xxxType 38 }
cevC7500AIP     OBJECT IDENTIFIER ::= { cevModuleC7xxxType 58 }
cevC7500CIP     OBJECT IDENTIFIER ::= { cevModuleC7xxxType 59 }
cevC7500CIP2    OBJECT IDENTIFIER ::= { cevModuleC7xxxType 60 }
cevC7500GEIP    OBJECT IDENTIFIER ::= { cevModuleC7xxxType 61 }
cevC7500FEIP    OBJECT IDENTIFIER ::= { cevModuleC7xxxType 62 }
cevC7xxxSIP     OBJECT IDENTIFIER ::= { cevModuleC7xxxType 63 }
cevC7xxxRSP     OBJECT IDENTIFIER ::= { cevModuleC7xxxType 64 }
cevC7xxxHSSI    OBJECT IDENTIFIER ::= { cevModuleC7xxxType 65 }
cevC7411        OBJECT IDENTIFIER ::= { cevModuleC7xxxType 66 }
cevC7411IoGE    OBJECT IDENTIFIER ::= { cevModuleC7xxxType 67 }
cevVip680       OBJECT IDENTIFIER ::= { cevModuleC7xxxType 70 }
cevModuleC4xxxType OBJECT IDENTIFIER ::= { cevModule 8 }
cevC4xxxUnknown OBJECT IDENTIFIER ::= { cevModuleC4xxxType 1 }
cevC4xxxNp4Gb   OBJECT IDENTIFIER ::= { cevModuleC4xxxType 2 }
cevModuleAS5200Type OBJECT IDENTIFIER ::= { cevModule 9 }
cevAS5200Carrier OBJECT IDENTIFIER ::= { cevModuleAS5200Type 1 }
cevAS5200DtdCarrier OBJECT IDENTIFIER ::= { cevModuleAS5200Type 2 }
cevPmAS5xxx12m56k OBJECT IDENTIFIER ::= { cevModuleAS5200Type 3 }
cevPmAS5xxx12mV110 OBJECT IDENTIFIER ::= { cevModuleAS5200Type 4 }
cevModuleC25xxType OBJECT IDENTIFIER ::= { cevModule 10 }
cevModuleAS5300Type OBJECT IDENTIFIER ::= { cevModule 11 }
cevAS53004ct1   OBJECT IDENTIFIER ::= { cevModuleAS5300Type 1 }
cevAS53004ce1   OBJECT IDENTIFIER ::= { cevModuleAS5300Type 2 }
cevPmDtdCarrier OBJECT IDENTIFIER ::= { cevModuleAS5300Type 3 }
cevPmDtd6m      OBJECT IDENTIFIER ::= { cevModuleAS5300Type 4 }
cevAS5300Carrier OBJECT IDENTIFIER ::= { cevModuleAS5300Type 5 }
cevPmAS5xxx12m  OBJECT IDENTIFIER ::= { cevModuleAS5300Type 6 }
cevAS5300VoiceCarrierCard OBJECT IDENTIFIER ::= { cevModuleAS5300Type 7 }
cevAS5300Dspmc542 OBJECT IDENTIFIER ::= { cevModuleAS5300Type 8 }
cevAS5300Dsp    OBJECT IDENTIFIER ::= { cevModuleAS5300Type 9 }
cevAS5300PmDtd12m OBJECT IDENTIFIER ::= { cevModuleAS5300Type 10 }
cevAS53008ct14t OBJECT IDENTIFIER ::= { cevModuleAS5300Type 11 }
cevAS53008ce14t OBJECT IDENTIFIER ::= { cevModuleAS5300Type 12 }
cevAS53004ct14t OBJECT IDENTIFIER ::= { cevModuleAS5300Type 13 }
cevAS53004ce14t OBJECT IDENTIFIER ::= { cevModuleAS5300Type 14 }
cevAS5300Amazon2Carrier OBJECT IDENTIFIER ::= { cevModuleAS5300Type 15 }
cevAS5300Dspm6c549 OBJECT IDENTIFIER ::= { cevModuleAS5300Type 16 }
cevModuleAS5800Type OBJECT IDENTIFIER ::= { cevModule 12 }
cevMAs5800Dsc   OBJECT IDENTIFIER ::= { cevModuleAS5800Type 1 }
cevMAs5800E1    OBJECT IDENTIFIER ::= { cevModuleAS5800Type 2 }
cevMAs5800T1    OBJECT IDENTIFIER ::= { cevModuleAS5800Type 3 }
cevMAs5800MicaHmm OBJECT IDENTIFIER ::= { cevModuleAS5800Type 4 }
cevMAs5800T3    OBJECT IDENTIFIER ::= { cevModuleAS5800Type 5 }
cevMAs5800FeDsi OBJECT IDENTIFIER ::= { cevModuleAS5800Type 6 }
cevMAs5800MicaDmm OBJECT IDENTIFIER ::= { cevModuleAS5800Type 7 }
cevMAs5800Vcc   OBJECT IDENTIFIER ::= { cevModuleAS5800Type 8 }
cevMAs5800Dspm6c549 OBJECT IDENTIFIER ::= { cevModuleAS5800Type 9 }
cevMAs5800Dsp   OBJECT IDENTIFIER ::= { cevModuleAS5800Type 10 }
cevModuleFabricType OBJECT IDENTIFIER ::= { cevModule 14 }
cev12012Sfc     OBJECT IDENTIFIER ::= { cevModuleFabricType 3 }
cev12012Csc     OBJECT IDENTIFIER ::= { cevModuleFabricType 4 }
cev12008Sfc8    OBJECT IDENTIFIER ::= { cevModuleFabricType 5 }
cev12008Csc8    OBJECT IDENTIFIER ::= { cevModuleFabricType 6 }
cev12016Sfc16   OBJECT IDENTIFIER ::= { cevModuleFabricType 7 }
cev12016Sfc16Oc192 OBJECT IDENTIFIER ::= { cevModuleFabricType 9 }
cev12016Csc16Oc192 OBJECT IDENTIFIER ::= { cevModuleFabricType 10 }
cev12010Sfc10   OBJECT IDENTIFIER ::= { cevModuleFabricType 11 }
cev12010Csc10   OBJECT IDENTIFIER ::= { cevModuleFabricType 12 }
cev12406Sfc6    OBJECT IDENTIFIER ::= { cevModuleFabricType 13 }
cev12406Csc6    OBJECT IDENTIFIER ::= { cevModuleFabricType 14 }
cev12410Sfc10   OBJECT IDENTIFIER ::= { cevModuleFabricType 15 }
cev12410Csc10   OBJECT IDENTIFIER ::= { cevModuleFabricType 16 }
cev12404Csc64   OBJECT IDENTIFIER ::= { cevModuleFabricType 17 }
cevModuleDaughterCard OBJECT IDENTIFIER ::= { cevModule 15 }
cevDspmPvdm3    OBJECT IDENTIFIER ::= { cevModuleDaughterCard 7 }
cevDspmPvdm1    OBJECT IDENTIFIER ::= { cevModuleDaughterCard 12 }
cevDspmPvdm2    OBJECT IDENTIFIER ::= { cevModuleDaughterCard 13 }
cevDspmPvdm4    OBJECT IDENTIFIER ::= { cevModuleDaughterCard 14 }
cevDspmPvdm5    OBJECT IDENTIFIER ::= { cevModuleDaughterCard 15 }
cevHdv8fxs      OBJECT IDENTIFIER ::= { cevModuleDaughterCard 17 }
cevHdv4dsp      OBJECT IDENTIFIER ::= { cevModuleDaughterCard 18 }
cevCeScsi2636   OBJECT IDENTIFIER ::= { cevModuleDaughterCard 24 }
cevCeIde2636    OBJECT IDENTIFIER ::= { cevModuleDaughterCard 25 }
cevVic4vpFxs4Did OBJECT IDENTIFIER ::= { cevModuleDaughterCard 26 }
cevModuleGBICs  OBJECT IDENTIFIER ::= { cevModule 16 }
cevMGBIC1000BaseLX OBJECT IDENTIFIER ::= { cevModuleGBICs 1 }
cevMGBIC1000BaseSX OBJECT IDENTIFIER ::= { cevModuleGBICs 2 }
cevMGBIC1000BaseCX OBJECT IDENTIFIER ::= { cevModuleGBICs 3 }
cevModuleC6xxxType OBJECT IDENTIFIER ::= { cevModule 17 }
cevC6xxxSlcCap8 OBJECT IDENTIFIER ::= { cevModuleC6xxxType 1 }
cevC6xxxNtcOc3si OBJECT IDENTIFIER ::= { cevModuleC6xxxType 2 }
cevC6xxxNtcOc3mm OBJECT IDENTIFIER ::= { cevModuleC6xxxType 3 }
cevC6xxxNtcStm1si OBJECT IDENTIFIER ::= { cevModuleC6xxxType 4 }
cevC6xxxNtcStm1mm OBJECT IDENTIFIER ::= { cevModuleC6xxxType 5 }
cevC6xxxSlcDmt8 OBJECT IDENTIFIER ::= { cevModuleC6xxxType 6 }
cevC6xxxSlcDmt16 OBJECT IDENTIFIER ::= { cevModuleC6xxxType 7 }
cevC6xxxNtcDs3  OBJECT IDENTIFIER ::= { cevModuleC6xxxType 8 }
cevC6xxxOsm1Oc48PosSs OBJECT IDENTIFIER ::= { cevModuleC6xxxType 10 }
cevC6xxxOsm1Oc48PosSl OBJECT IDENTIFIER ::= { cevModuleC6xxxType 11 }
cevC6xxxOsm1Oc48PosSi OBJECT IDENTIFIER ::= { cevModuleC6xxxType 12 }
cevC6xxxOsm2Oc12PosSl OBJECT IDENTIFIER ::= { cevModuleC6xxxType 15 }
cevC6xxxOsm4Oc12PosSl OBJECT IDENTIFIER ::= { cevModuleC6xxxType 16 }
cevC6xxxOsm2Oc12PosMm OBJECT IDENTIFIER ::= { cevModuleC6xxxType 17 }
cevC6xxxOsm4Oc12PosMm OBJECT IDENTIFIER ::= { cevModuleC6xxxType 18 }
cevC6xxxOsm2Oc12PosSi OBJECT IDENTIFIER ::= { cevModuleC6xxxType 19 }
cevC6xxxOsm4Oc12PosSi OBJECT IDENTIFIER ::= { cevModuleC6xxxType 20 }
cevC6xxxOsm8Oc3PosSi OBJECT IDENTIFIER ::= { cevModuleC6xxxType 21 }
cevC6xxxOsm16Oc3PosSi OBJECT IDENTIFIER ::= { cevModuleC6xxxType 22 }
cevC6xxxOsm8Oc3PosMm OBJECT IDENTIFIER ::= { cevModuleC6xxxType 23 }
cevC6xxxOsm16Oc3PosMm OBJECT IDENTIFIER ::= { cevModuleC6xxxType 24 }
cevC6xxxOsm8Oc3PosSl OBJECT IDENTIFIER ::= { cevModuleC6xxxType 25 }
cevC6xxxOsm16Oc3PosSl OBJECT IDENTIFIER ::= { cevModuleC6xxxType 26 }
cevC6xxx4GeWanGbic OBJECT IDENTIFIER ::= { cevModuleC6xxxType 27 }
cevC6xxxOsm4ge4oc12ChDs3SmIr OBJECT IDENTIFIER ::= { cevModuleC6xxxType 31 }
cevC6xxxOsm4ge8oc12ChDs3SmIr OBJECT IDENTIFIER ::= { cevModuleC6xxxType 32 }
cevC6xxxOsm4geoc48ChDs3SmSr OBJECT IDENTIFIER ::= { cevModuleC6xxxType 33 }
ceC6xxxOsm4ge2oc48ChDs3SmSr OBJECT IDENTIFIER ::= { cevModuleC6xxxType 34 }
cevC6xxxOsm4geoc48ChDs3SmIr OBJECT IDENTIFIER ::= { cevModuleC6xxxType 35 }
cevC6xxxOsm4ge2oc48ChDs3SmIr OBJECT IDENTIFIER ::= { cevModuleC6xxxType 36 }
cevC6xxxOsm4geoc12ChDs3SmIr OBJECT IDENTIFIER ::= { cevModuleC6xxxType 37 }
cevC6xxxOsm4ge2oc12ChDs3SmIr OBJECT IDENTIFIER ::= { cevModuleC6xxxType 38 }
cevModuleGsrType OBJECT IDENTIFIER ::= { cevModule 18 }
cevGsrOc12Chsts3Mm OBJECT IDENTIFIER ::= { cevModuleGsrType 1 }
cevGsrOc12Chsts3Sm OBJECT IDENTIFIER ::= { cevModuleGsrType 2 }
cevPosOc48SmLrFc OBJECT IDENTIFIER ::= { cevModuleGsrType 5 }
cevPosQoc3SmL   OBJECT IDENTIFIER ::= { cevModuleGsrType 6 }
cevGsr8feTx     OBJECT IDENTIFIER ::= { cevModuleGsrType 13 }
cevGsr8feFx     OBJECT IDENTIFIER ::= { cevModuleGsrType 14 }
cevPosQoc12SmLr OBJECT IDENTIFIER ::= { cevModuleGsrType 17 }
cevPosQoc12MmSr OBJECT IDENTIFIER ::= { cevModuleGsrType 18 }
cevPosOc48SmSrFc OBJECT IDENTIFIER ::= { cevModuleGsrType 19 }
cevPosOc48SmLrSc OBJECT IDENTIFIER ::= { cevModuleGsrType 20 }
cevPosOc48SmSrSc OBJECT IDENTIFIER ::= { cevModuleGsrType 21 }
cevSrpOc12SmIr  OBJECT IDENTIFIER ::= { cevModuleGsrType 22 }
cevSrpOc12SmLr  OBJECT IDENTIFIER ::= { cevModuleGsrType 23 }
cevSrpOc12Mm    OBJECT IDENTIFIER ::= { cevModuleGsrType 24 }
cevPosEnOc48SrSc OBJECT IDENTIFIER ::= { cevModuleGsrType 25 }
cevPosEnOc48SrFc OBJECT IDENTIFIER ::= { cevModuleGsrType 26 }
cevPosEnOc48LrSc OBJECT IDENTIFIER ::= { cevModuleGsrType 27 }
cevPosEnOc48LrFc OBJECT IDENTIFIER ::= { cevModuleGsrType 28 }
cevPosEnQoc12Sr OBJECT IDENTIFIER ::= { cevModuleGsrType 29 }
cevPosEnQoc12Ir OBJECT IDENTIFIER ::= { cevModuleGsrType 30 }
cevCopper6ds3   OBJECT IDENTIFIER ::= { cevModuleGsrType 31 }
cevCopper12ds3  OBJECT IDENTIFIER ::= { cevModuleGsrType 32 }
cevPos4Oc3Mm    OBJECT IDENTIFIER ::= { cevModuleGsrType 37 }
cevPos4Oc3Sm    OBJECT IDENTIFIER ::= { cevModuleGsrType 38 }
cevPosOc12Mm    OBJECT IDENTIFIER ::= { cevModuleGsrType 39 }
cevPosOc12Sm    OBJECT IDENTIFIER ::= { cevModuleGsrType 40 }
cevAtmOc12Mm    OBJECT IDENTIFIER ::= { cevModuleGsrType 41 }
cevAtmOc12Sm    OBJECT IDENTIFIER ::= { cevModuleGsrType 42 }
cevPosOc48MmL   OBJECT IDENTIFIER ::= { cevModuleGsrType 43 }
cevAtm4Oc3Sm    OBJECT IDENTIFIER ::= { cevModuleGsrType 44 }
cevAtm4Oc3Mm    OBJECT IDENTIFIER ::= { cevModuleGsrType 45 }
cevOc12ChDs3Mm  OBJECT IDENTIFIER ::= { cevModuleGsrType 46 }
cevOc12ChDs3Sm  OBJECT IDENTIFIER ::= { cevModuleGsrType 47 }
cevGsrGe        OBJECT IDENTIFIER ::= { cevModuleGsrType 48 }
cevGsr3ge       OBJECT IDENTIFIER ::= { cevModuleGsrType 49 }
cevGsrAlarm16   OBJECT IDENTIFIER ::= { cevModuleGsrType 50 }
cevGsrBusBoard16 OBJECT IDENTIFIER ::= { cevModuleGsrType 51 }
cevSrpOc12SmXr  OBJECT IDENTIFIER ::= { cevModuleGsrType 52 }
cevPosEnQoc12Mm OBJECT IDENTIFIER ::= { cevModuleGsrType 53 }
cevPosEnQoc48SmSrFc OBJECT IDENTIFIER ::= { cevModuleGsrType 54 }
cevPosEnQoc48SmSrSc OBJECT IDENTIFIER ::= { cevModuleGsrType 55 }
cevPosEnQoc48SmLrSc OBJECT IDENTIFIER ::= { cevModuleGsrType 56 }
cevPosEnQoc48SmLrFc OBJECT IDENTIFIER ::= { cevModuleGsrType 57 }
cevPosEnOc192SmLrFc OBJECT IDENTIFIER ::= { cevModuleGsrType 59 }
cevPosEnOc192SmLrSc OBJECT IDENTIFIER ::= { cevModuleGsrType 60 }
cevPosEnOc192SmVsrSc OBJECT IDENTIFIER ::= { cevModuleGsrType 61 }
cevPosEnOc192SmVsrFc OBJECT IDENTIFIER ::= { cevModuleGsrType 62 }
cevGsr2Oc3ChDs1 OBJECT IDENTIFIER ::= { cevModuleGsrType 74 }
cevGsrAlarm10   OBJECT IDENTIFIER ::= { cevModuleGsrType 81 }
cevGsrBusBoard10 OBJECT IDENTIFIER ::= { cevModuleGsrType 82 }
cevCopper6e3    OBJECT IDENTIFIER ::= { cevModuleGsrType 88 }
cevCopper12e3   OBJECT IDENTIFIER ::= { cevModuleGsrType 89 }
cevGsrAlarm6    OBJECT IDENTIFIER ::= { cevModuleGsrType 96 }
cevPosEnQoc48Vsr OBJECT IDENTIFIER ::= { cevModuleGsrType 97 }
cevPosEnQoc48MmSrSc OBJECT IDENTIFIER ::= { cevModuleGsrType 98 }
cevPosEnQoc48SmIrSc OBJECT IDENTIFIER ::= { cevModuleGsrType 99 }
cevPosEnQoc48SmIrFc OBJECT IDENTIFIER ::= { cevModuleGsrType 100 }
cevPosEnQoc48SmVlrSc OBJECT IDENTIFIER ::= { cevModuleGsrType 101 }
cevPosEnQoc48SmVlrFc OBJECT IDENTIFIER ::= { cevModuleGsrType 102 }
cevPosEnQoc48SmElrSc OBJECT IDENTIFIER ::= { cevModuleGsrType 103 }
cevPosEnQoc48SmElrFc OBJECT IDENTIFIER ::= { cevModuleGsrType 104 }
cevPosEnOc192Vsr OBJECT IDENTIFIER ::= { cevModuleGsrType 105 }
cevPosEnOc192SmSr2Sc OBJECT IDENTIFIER ::= { cevModuleGsrType 106 }
cevPosEnOc192SmSr2Fc OBJECT IDENTIFIER ::= { cevModuleGsrType 107 }
cevPosEnOc192SmVlrSc OBJECT IDENTIFIER ::= { cevModuleGsrType 108 }
cevPosEnOc192SmVlrFc OBJECT IDENTIFIER ::= { cevModuleGsrType 109 }
cevPosEnOc192SmElrSc OBJECT IDENTIFIER ::= { cevModuleGsrType 110 }
cevPosEnOc192SmElrFc OBJECT IDENTIFIER ::= { cevModuleGsrType 111 }
cevGsrEOc192SmLrSc OBJECT IDENTIFIER ::= { cevModuleGsrType 116 }
cevGsrEOc192SmVsrSc OBJECT IDENTIFIER ::= { cevModuleGsrType 117 }
cevGsrEOc192SmVsrFc OBJECT IDENTIFIER ::= { cevModuleGsrType 118 }
cevGsrEOc192SmSrFc OBJECT IDENTIFIER ::= { cevModuleGsrType 119 }
cevGsrEOc192SmSrSc OBJECT IDENTIFIER ::= { cevModuleGsrType 120 }
cevGsrEOc192SmLrFc OBJECT IDENTIFIER ::= { cevModuleGsrType 121 }
cevGsrEQoc48SmLrFc OBJECT IDENTIFIER ::= { cevModuleGsrType 122 }
cevGsrEQoc48SmLrSc OBJECT IDENTIFIER ::= { cevModuleGsrType 123 }
cevGsrEQoc48SmVsrSc OBJECT IDENTIFIER ::= { cevModuleGsrType 124 }
cevGsrEQoc48SmVsrFc OBJECT IDENTIFIER ::= { cevModuleGsrType 125 }
cevGsrEQoc48SmSrFc OBJECT IDENTIFIER ::= { cevModuleGsrType 126 }
cevGsrEQoc48SmSrSc OBJECT IDENTIFIER ::= { cevModuleGsrType 127 }
cevGsrEQoc48Vsr OBJECT IDENTIFIER ::= { cevModuleGsrType 128 }
cevGsrEQoc48SmSr2Sc OBJECT IDENTIFIER ::= { cevModuleGsrType 129 }
cevGsrEQoc48SmSr2Fc OBJECT IDENTIFIER ::= { cevModuleGsrType 130 }
cevGsrEQoc48MmSrSc OBJECT IDENTIFIER ::= { cevModuleGsrType 131 }
cevGsrEQoc48SmIrSc OBJECT IDENTIFIER ::= { cevModuleGsrType 132 }
cevGsrEQoc48SmIrFc OBJECT IDENTIFIER ::= { cevModuleGsrType 133 }
cevGsrEQoc48SmVlrSc OBJECT IDENTIFIER ::= { cevModuleGsrType 134 }
cevGsrEQoc48SmVlrFc OBJECT IDENTIFIER ::= { cevModuleGsrType 135 }
cevGsrEQoc48SmElrSc OBJECT IDENTIFIER ::= { cevModuleGsrType 136 }
cevGsrEQoc48SmElrFc OBJECT IDENTIFIER ::= { cevModuleGsrType 137 }
cevGsrEOc192Vsr OBJECT IDENTIFIER ::= { cevModuleGsrType 138 }
cevGsrEOc192SmSr2Sc OBJECT IDENTIFIER ::= { cevModuleGsrType 139 }
cevGsrEOc192SmSr2Fc OBJECT IDENTIFIER ::= { cevModuleGsrType 140 }
cevGsrEOc192MmSrSc OBJECT IDENTIFIER ::= { cevModuleGsrType 141 }
cevGsrEOc192SmIrSc OBJECT IDENTIFIER ::= { cevModuleGsrType 142 }
cevGsrEOc192SmIrFc OBJECT IDENTIFIER ::= { cevModuleGsrType 143 }
cevGsrEOc192SmVlrSc OBJECT IDENTIFIER ::= { cevModuleGsrType 144 }
cevGsrEOc192SmVlrFc OBJECT IDENTIFIER ::= { cevModuleGsrType 145 }
cevGsrEOc192SmElrSc OBJECT IDENTIFIER ::= { cevModuleGsrType 146 }
cevGsrEOc192SmElrFc OBJECT IDENTIFIER ::= { cevModuleGsrType 147 }
cevSsrp2Oc48SrpSmSrLc OBJECT IDENTIFIER ::= { cevModuleGsrType 148 }
cevSsrp2Oc48SrpSmIrLc OBJECT IDENTIFIER ::= { cevModuleGsrType 149 }
cevSsrp2Oc48SrpSmLrLc OBJECT IDENTIFIER ::= { cevModuleGsrType 150 }
cevSsrp2Oc48PosSmSrLc OBJECT IDENTIFIER ::= { cevModuleGsrType 151 }
cevSsrp2Oc48PosSmIrLc OBJECT IDENTIFIER ::= { cevModuleGsrType 152 }
cevSsrp2Oc48PosSmLrLc OBJECT IDENTIFIER ::= { cevModuleGsrType 153 }
cevGsrGeFe      OBJECT IDENTIFIER ::= { cevModuleGsrType 156 }
cevGsrAtmEn8Oc3Mm OBJECT IDENTIFIER ::= { cevModuleGsrType 174 }
cevModuleRpmType OBJECT IDENTIFIER ::= { cevModule 19 }
cevAtmdxRpm     OBJECT IDENTIFIER ::= { cevModuleRpmType 1 }
cevModuleCat8500Type OBJECT IDENTIFIER ::= { cevModule 20 }
cevCat8500CpuSwitch OBJECT IDENTIFIER ::= { cevModuleCat8500Type 1 }
cevCat8500FeatureFpga OBJECT IDENTIFIER ::= { cevModuleCat8500Type 2 }
cevCat8500FeatureAsic OBJECT IDENTIFIER ::= { cevModuleCat8500Type 3 }
cevCat8500FeaturePVC OBJECT IDENTIFIER ::= { cevModuleCat8500Type 4 }
cevCat8500FeUTP8p16k OBJECT IDENTIFIER ::= { cevModuleCat8500Type 5 }
cevCat8500FeUTP8p64k OBJECT IDENTIFIER ::= { cevModuleCat8500Type 6 }
cevCat8500FeMMF8p16k OBJECT IDENTIFIER ::= { cevModuleCat8500Type 7 }
cevCat8500FeMMF8p64k OBJECT IDENTIFIER ::= { cevModuleCat8500Type 8 }
cevCat8500FeUTP16p16k OBJECT IDENTIFIER ::= { cevModuleCat8500Type 9 }
cevCat8500FeUTP16p64k OBJECT IDENTIFIER ::= { cevModuleCat8500Type 10 }
cevCat8500FeMMF16p16k OBJECT IDENTIFIER ::= { cevModuleCat8500Type 11 }
cevCat8500FeMMF16p64k OBJECT IDENTIFIER ::= { cevModuleCat8500Type 12 }
cevCat8500GeF1p16k OBJECT IDENTIFIER ::= { cevModuleCat8500Type 13 }
cevCat8500GeF1p64k OBJECT IDENTIFIER ::= { cevModuleCat8500Type 14 }
cevCat8500GeF2p16k OBJECT IDENTIFIER ::= { cevModuleCat8500Type 15 }
cevCat8500GeF2p64k OBJECT IDENTIFIER ::= { cevModuleCat8500Type 16 }
cevCat8500FeBridge4p OBJECT IDENTIFIER ::= { cevModuleCat8500Type 17 }
cevCat8500RouteProc OBJECT IDENTIFIER ::= { cevModuleCat8500Type 18 }
cevCat8500Switch10GProc OBJECT IDENTIFIER ::= { cevModuleCat8500Type 19 }
cevCat8500FeatureNetClock OBJECT IDENTIFIER ::= { cevModuleCat8500Type 20 }
cevCat8500FeatureABR OBJECT IDENTIFIER ::= { cevModuleCat8500Type 21 }
cevCat8500FeatureLite OBJECT IDENTIFIER ::= { cevModuleCat8500Type 22 }
cevCat8500m16pOC3Mm OBJECT IDENTIFIER ::= { cevModuleCat8500Type 23 }
cevCat8500m16pOC3Sm OBJECT IDENTIFIER ::= { cevModuleCat8500Type 24 }
cevCat8500m4pOC12Mm OBJECT IDENTIFIER ::= { cevModuleCat8500Type 25 }
cevCat8500m4pOC12Sm OBJECT IDENTIFIER ::= { cevModuleCat8500Type 26 }
cevCat8500m4pOC3Utp5 OBJECT IDENTIFIER ::= { cevModuleCat8500Type 27 }
cevCat8500m4pOC3Mixed OBJECT IDENTIFIER ::= { cevModuleCat8500Type 28 }
cevCat8500m4pOC3Sm OBJECT IDENTIFIER ::= { cevModuleCat8500Type 29 }
cevCat8500m4pOC3Mm OBJECT IDENTIFIER ::= { cevModuleCat8500Type 30 }
cevCat8500mATM25 OBJECT IDENTIFIER ::= { cevModuleCat8500Type 31 }
cevCat8500m4pE3 OBJECT IDENTIFIER ::= { cevModuleCat8500Type 32 }
cevCat8500m4pDs3 OBJECT IDENTIFIER ::= { cevModuleCat8500Type 33 }
cevCat8500mCbr75E1 OBJECT IDENTIFIER ::= { cevModuleCat8500Type 34 }
cevCat8500mCbr120E1 OBJECT IDENTIFIER ::= { cevModuleCat8500Type 35 }
cevCat8500mCbrT1 OBJECT IDENTIFIER ::= { cevModuleCat8500Type 36 }
cevCat8500mE1   OBJECT IDENTIFIER ::= { cevModuleCat8500Type 37 }
cevCat8500mT1   OBJECT IDENTIFIER ::= { cevModuleCat8500Type 38 }
cevCat8500mE1Bnc OBJECT IDENTIFIER ::= { cevModuleCat8500Type 39 }
cevCat8500mE3   OBJECT IDENTIFIER ::= { cevModuleCat8500Type 40 }
cevCat8500mDs3  OBJECT IDENTIFIER ::= { cevModuleCat8500Type 41 }
cevCat8500m4pFrCE1 OBJECT IDENTIFIER ::= { cevModuleCat8500Type 42 }
cevCat8500m1pFrCT3 OBJECT IDENTIFIER ::= { cevModuleCat8500Type 43 }
cevCat8500GeF8p64k OBJECT IDENTIFIER ::= { cevModuleCat8500Type 44 }
cevCat8500mArm1p64k OBJECT IDENTIFIER ::= { cevModuleCat8500Type 45 }
cevCat8500mArm2p64k OBJECT IDENTIFIER ::= { cevModuleCat8500Type 46 }
cevCat8500mOC48c1pSm OBJECT IDENTIFIER ::= { cevModuleCat8500Type 47 }
cevCat8500mIma8pT1 OBJECT IDENTIFIER ::= { cevModuleCat8500Type 48 }
cevCat8500mIma8pE1 OBJECT IDENTIFIER ::= { cevModuleCat8500Type 49 }
cevCat8500mATM25m4p OBJECT IDENTIFIER ::= { cevModuleCat8500Type 50 }
cevCat8500mOC121pMm OBJECT IDENTIFIER ::= { cevModuleCat8500Type 51 }
cevCat8500mOC121pSm OBJECT IDENTIFIER ::= { cevModuleCat8500Type 52 }
cevCat8500m1pOC12Mixed OBJECT IDENTIFIER ::= { cevModuleCat8500Type 53 }
cevCat8500mFimBridge OBJECT IDENTIFIER ::= { cevModuleCat8500Type 54 }
cevCat8500mFimOC12Mm OBJECT IDENTIFIER ::= { cevModuleCat8500Type 55 }
cevCat8500Ge1pXpif16k OBJECT IDENTIFIER ::= { cevModuleCat8500Type 56 }
cevCat8500Ge1pXpif64k OBJECT IDENTIFIER ::= { cevModuleCat8500Type 57 }
cevCat8500Ge1pXpif256k OBJECT IDENTIFIER ::= { cevModuleCat8500Type 58 }
cevCat8500Atm1pXpif64kOc12SmIr OBJECT IDENTIFIER ::= { cevModuleCat8500Type 59 }
cevCat8500Atm1pXpif256kOc12SmIr OBJECT IDENTIFIER ::= { cevModuleCat8500Type 60 }
cevCat8500Atm1pXpif64kOc12Mm OBJECT IDENTIFIER ::= { cevModuleCat8500Type 61 }
cevCat8500Atm1pXpif256kOc12Mm OBJECT IDENTIFIER ::= { cevModuleCat8500Type 62 }
cevCat8500Atm1pXpif64kOc3SmIr OBJECT IDENTIFIER ::= { cevModuleCat8500Type 63 }
cevCat8500Atm1pXpif256kOc3SmIr OBJECT IDENTIFIER ::= { cevModuleCat8500Type 64 }
cevCat8500Atm1pXpif64kOc3Mm OBJECT IDENTIFIER ::= { cevModuleCat8500Type 65 }
cevCat8500Atm1pXpif256kOc3Mm OBJECT IDENTIFIER ::= { cevModuleCat8500Type 66 }
cevCat8500Pos1pXpif64kOc12SmIr OBJECT IDENTIFIER ::= { cevModuleCat8500Type 67 }
cevCat8500Pos1pXpif256kOc12SmIr OBJECT IDENTIFIER ::= { cevModuleCat8500Type 68 }
cevCat8500Pos1pXpif64kOc12SmLr OBJECT IDENTIFIER ::= { cevModuleCat8500Type 69 }
cevCat8500Pos1pXpif256kOc12SmLr OBJECT IDENTIFIER ::= { cevModuleCat8500Type 70 }
cevModuleWASCommonCards OBJECT IDENTIFIER ::= { cevModule 21 }
cevAusm8t1      OBJECT IDENTIFIER ::= { cevModuleWASCommonCards 1 }
cevAusm8e1      OBJECT IDENTIFIER ::= { cevModuleWASCommonCards 2 }
cevCesm8t1      OBJECT IDENTIFIER ::= { cevModuleWASCommonCards 3 }
cevCesm8e1      OBJECT IDENTIFIER ::= { cevModuleWASCommonCards 4 }
cevFrsm8t1      OBJECT IDENTIFIER ::= { cevModuleWASCommonCards 5 }
cevFrsm8e1      OBJECT IDENTIFIER ::= { cevModuleWASCommonCards 6 }
cevFrsm4x21     OBJECT IDENTIFIER ::= { cevModuleWASCommonCards 7 }
cevFrsm2hssi    OBJECT IDENTIFIER ::= { cevModuleWASCommonCards 8 }
cevAxsm1Oc48    OBJECT IDENTIFIER ::= { cevModuleWASCommonCards 9 }
cevAxsm4Oc12    OBJECT IDENTIFIER ::= { cevModuleWASCommonCards 10 }
cevAxsm8Oc3     OBJECT IDENTIFIER ::= { cevModuleWASCommonCards 11 }
cevAxsm16Oc3    OBJECT IDENTIFIER ::= { cevModuleWASCommonCards 12 }
cevAxsm16T3E3   OBJECT IDENTIFIER ::= { cevModuleWASCommonCards 13 }
cevCesm1t3      OBJECT IDENTIFIER ::= { cevModuleWASCommonCards 14 }
cevCesm1e3      OBJECT IDENTIFIER ::= { cevModuleWASCommonCards 15 }
cevVism8t1      OBJECT IDENTIFIER ::= { cevModuleWASCommonCards 16 }
cevVism8e1      OBJECT IDENTIFIER ::= { cevModuleWASCommonCards 17 }
cevMGXRpm       OBJECT IDENTIFIER ::= { cevModuleWASCommonCards 18 }
cevMGXSrm3t3    OBJECT IDENTIFIER ::= { cevModuleWASCommonCards 19 }
cevEnhAxsm8oc3  OBJECT IDENTIFIER ::= { cevModuleWASCommonCards 23 }
cevEnhAxsm16t3e3 OBJECT IDENTIFIER ::= { cevModuleWASCommonCards 27 }
cevAxsm2oc12    OBJECT IDENTIFIER ::= { cevModuleWASCommonCards 32 }
cevFrsm4V35     OBJECT IDENTIFIER ::= { cevModuleWASCommonCards 38 }
cevFrsm2Ct3     OBJECT IDENTIFIER ::= { cevModuleWASCommonCards 39 }
cevFrsm2t3      OBJECT IDENTIFIER ::= { cevModuleWASCommonCards 40 }
cevFrsm2e3      OBJECT IDENTIFIER ::= { cevModuleWASCommonCards 41 }
cevAusmB8t1     OBJECT IDENTIFIER ::= { cevModuleWASCommonCards 42 }
cevAusmB8e1     OBJECT IDENTIFIER ::= { cevModuleWASCommonCards 43 }
cevVismPr8t1    OBJECT IDENTIFIER ::= { cevModuleWASCommonCards 70 }
cevVismPr8e1    OBJECT IDENTIFIER ::= { cevModuleWASCommonCards 71 }
cevAxsm2Oc48    OBJECT IDENTIFIER ::= { cevModuleWASCommonCards 73 }
cevAxsm8Oc12    OBJECT IDENTIFIER ::= { cevModuleWASCommonCards 74 }
cevVxsm4Oc3     OBJECT IDENTIFIER ::= { cevModuleWASCommonCards 81 }
cevMGXSrm4Oc3   OBJECT IDENTIFIER ::= { cevModuleWASCommonCards 82 }
cevModule38xxType OBJECT IDENTIFIER ::= { cevModule 22 }
cevMc3810Vcm3   OBJECT IDENTIFIER ::= { cevModule38xxType 1 }
cevMc3810Bvm    OBJECT IDENTIFIER ::= { cevModule38xxType 2 }
cevMc3810AvmFxoUk OBJECT IDENTIFIER ::= { cevModule38xxType 3 }
cevMc3810AvmFxoGer OBJECT IDENTIFIER ::= { cevModule38xxType 4 }
cevMc3810Hcm2   OBJECT IDENTIFIER ::= { cevModule38xxType 5 }
cevMc3810Hcm6   OBJECT IDENTIFIER ::= { cevModule38xxType 6 }
cevMc3810AvmFxoPr3 OBJECT IDENTIFIER ::= { cevModule38xxType 7 }
cevMc3810AvmFxoPr2 OBJECT IDENTIFIER ::= { cevModule38xxType 8 }
cevMc3810Vdm    OBJECT IDENTIFIER ::= { cevModule38xxType 9 }
cevMc3810ApmFxsDid OBJECT IDENTIFIER ::= { cevModule38xxType 10 }
cevMc3810BvmNtTe OBJECT IDENTIFIER ::= { cevModule38xxType 11 }
cevMc3810Hcm1   OBJECT IDENTIFIER ::= { cevModule38xxType 12 }
cevMc3810Hcm3   OBJECT IDENTIFIER ::= { cevModule38xxType 13 }
cevMc3810Hcm4   OBJECT IDENTIFIER ::= { cevModule38xxType 14 }
cevMc3810Hcm5   OBJECT IDENTIFIER ::= { cevModule38xxType 15 }
cevModuleCat29xxType OBJECT IDENTIFIER ::= { cevModule 23 }
cevX2914        OBJECT IDENTIFIER ::= { cevModuleCat29xxType 1 }
cevX2922        OBJECT IDENTIFIER ::= { cevModuleCat29xxType 2 }
cevX2914V       OBJECT IDENTIFIER ::= { cevModuleCat29xxType 3 }
cevX2922V       OBJECT IDENTIFIER ::= { cevModuleCat29xxType 4 }
cevX2924V       OBJECT IDENTIFIER ::= { cevModuleCat29xxType 5 }
cevX2951        OBJECT IDENTIFIER ::= { cevModuleCat29xxType 6 }
cevX2961        OBJECT IDENTIFIER ::= { cevModuleCat29xxType 7 }
cevX2971        OBJECT IDENTIFIER ::= { cevModuleCat29xxType 8 }
cevX2972        OBJECT IDENTIFIER ::= { cevModuleCat29xxType 9 }
cevX2931        OBJECT IDENTIFIER ::= { cevModuleCat29xxType 10 }
cevModuleOscillatorType OBJECT IDENTIFIER ::= { cevModule 24 }
cevStratum3     OBJECT IDENTIFIER ::= { cevModuleOscillatorType 1 }
cevStratum4     OBJECT IDENTIFIER ::= { cevModuleOscillatorType 2 }
cevModuleDslamType OBJECT IDENTIFIER ::= { cevModule 25 }
cevAtuc1p8DmtItemp OBJECT IDENTIFIER ::= { cevModuleDslamType 21 }
cevStuc1p8Itemp OBJECT IDENTIFIER ::= { cevModuleDslamType 22 }
cevModuleWASBackCards OBJECT IDENTIFIER ::= { cevModule 26 }
cevLmBnc2t3     OBJECT IDENTIFIER ::= { cevModuleWASBackCards 1 }
cevLmBnc2e3     OBJECT IDENTIFIER ::= { cevModuleWASBackCards 2 }
cevLmDb154x21   OBJECT IDENTIFIER ::= { cevModuleWASBackCards 3 }
cevLmScsi22hssi OBJECT IDENTIFIER ::= { cevModuleWASBackCards 4 }
cevLmRj488t1    OBJECT IDENTIFIER ::= { cevModuleWASBackCards 5 }
cevLmRj488t1R   OBJECT IDENTIFIER ::= { cevModuleWASBackCards 6 }
cevLmRj488e1    OBJECT IDENTIFIER ::= { cevModuleWASBackCards 7 }
cevLmRj488e1R   OBJECT IDENTIFIER ::= { cevModuleWASBackCards 8 }
cevLmSmb8e1     OBJECT IDENTIFIER ::= { cevModuleWASBackCards 9 }
cevLmSmb8e1R    OBJECT IDENTIFIER ::= { cevModuleWASBackCards 10 }
cevLmPsmUI      OBJECT IDENTIFIER ::= { cevModuleWASBackCards 11 }
cevLmMmf4oc3    OBJECT IDENTIFIER ::= { cevModuleWASBackCards 12 }
cevLmSmfIr4oc3  OBJECT IDENTIFIER ::= { cevModuleWASBackCards 13 }
cevLmSmfLr4oc3  OBJECT IDENTIFIER ::= { cevModuleWASBackCards 14 }
cevLmSmfIr1oc12 OBJECT IDENTIFIER ::= { cevModuleWASBackCards 15 }
cevLmSmfLr1oc12 OBJECT IDENTIFIER ::= { cevModuleWASBackCards 16 }
cevLmS3Ui       OBJECT IDENTIFIER ::= { cevModuleWASBackCards 17 }
cevLm1feTx      OBJECT IDENTIFIER ::= { cevModuleWASBackCards 18 }
cevLm1feFx      OBJECT IDENTIFIER ::= { cevModuleWASBackCards 19 }
cevLm1mmfFddi   OBJECT IDENTIFIER ::= { cevModuleWASBackCards 20 }
cevLm1smfFddi   OBJECT IDENTIFIER ::= { cevModuleWASBackCards 21 }
cevLmRj454e     OBJECT IDENTIFIER ::= { cevModuleWASBackCards 22 }
cevLmMmf8oc3    OBJECT IDENTIFIER ::= { cevModuleWASBackCards 23 }
cevLmSmfIr8oc3  OBJECT IDENTIFIER ::= { cevModuleWASBackCards 24 }
cevLmSmfLr8oc3  OBJECT IDENTIFIER ::= { cevModuleWASBackCards 25 }
cevLmSmfLr1oc48 OBJECT IDENTIFIER ::= { cevModuleWASBackCards 27 }
cevLmPsmHD      OBJECT IDENTIFIER ::= { cevModuleWASBackCards 28 }
cevLmSmb8t3     OBJECT IDENTIFIER ::= { cevModuleWASBackCards 29 }
cevLmSmb8e3     OBJECT IDENTIFIER ::= { cevModuleWASBackCards 30 }
cevLmSmb4stm1   OBJECT IDENTIFIER ::= { cevModuleWASBackCards 31 }
cevLmSmfIr2oc12 OBJECT IDENTIFIER ::= { cevModuleWASBackCards 32 }
cevLmSmfLr2oc12 OBJECT IDENTIFIER ::= { cevModuleWASBackCards 33 }
cevLmSmfSr1oc48 OBJECT IDENTIFIER ::= { cevModuleWASBackCards 34 }
cevLmSmfXlr1oc48 OBJECT IDENTIFIER ::= { cevModuleWASBackCards 35 }
cevLmBnc3t3     OBJECT IDENTIFIER ::= { cevModuleWASBackCards 36 }
cevLmSmfIr1Oc48B OBJECT IDENTIFIER ::= { cevModuleWASBackCards 37 }
cevLmSmfLr1Oc48B OBJECT IDENTIFIER ::= { cevModuleWASBackCards 38 }
cevLmSmfSr1Oc48B OBJECT IDENTIFIER ::= { cevModuleWASBackCards 39 }
cevLmSmfIr2Oc12B OBJECT IDENTIFIER ::= { cevModuleWASBackCards 40 }
cevLmSmfLr2Oc12B OBJECT IDENTIFIER ::= { cevModuleWASBackCards 41 }
cevLmSmfIr1Oc12C OBJECT IDENTIFIER ::= { cevModuleWASBackCards 42 }
cevLmSmfLr1Oc12C OBJECT IDENTIFIER ::= { cevModuleWASBackCards 43 }
cevLmMmf4Oc3C   OBJECT IDENTIFIER ::= { cevModuleWASBackCards 44 }
cevLmSmfIr4Oc3C OBJECT IDENTIFIER ::= { cevModuleWASBackCards 45 }
cevLmSmfLr4Oc3C OBJECT IDENTIFIER ::= { cevModuleWASBackCards 46 }
cevLmSmfXlr1Oc48B OBJECT IDENTIFIER ::= { cevModuleWASBackCards 51 }
cevModuleUbrType OBJECT IDENTIFIER ::= { cevModule 27 }
cevUbrMc16s     OBJECT IDENTIFIER ::= { cevModuleUbrType 2 }
cevUbrMc11      OBJECT IDENTIFIER ::= { cevModuleUbrType 3 }
cevUbrMc11c     OBJECT IDENTIFIER ::= { cevModuleUbrType 4 }
cevUbrMc12c     OBJECT IDENTIFIER ::= { cevModuleUbrType 5 }
cevUbrMc14c     OBJECT IDENTIFIER ::= { cevModuleUbrType 6 }
cevUbrMc16a     OBJECT IDENTIFIER ::= { cevModuleUbrType 7 }
cevUbrMc16b     OBJECT IDENTIFIER ::= { cevModuleUbrType 8 }
cevUbrMc16c     OBJECT IDENTIFIER ::= { cevModuleUbrType 9 }
cevUbrMc16e     OBJECT IDENTIFIER ::= { cevModuleUbrType 10 }
cevUbrMc28c     OBJECT IDENTIFIER ::= { cevModuleUbrType 11 }
cevUbrMc26      OBJECT IDENTIFIER ::= { cevModuleUbrType 12 }
cevUbr912C      OBJECT IDENTIFIER ::= { cevModuleUbrType 13 }
cevUbr912S      OBJECT IDENTIFIER ::= { cevModuleUbrType 14 }
cevUbr914R      OBJECT IDENTIFIER ::= { cevModuleUbrType 15 }
cevUbrClk       OBJECT IDENTIFIER ::= { cevModuleUbrType 16 }
cevUbr925       OBJECT IDENTIFIER ::= { cevModuleUbrType 17 }
cevUbrMc26c     OBJECT IDENTIFIER ::= { cevModuleUbrType 18 }
cevUbrMc28cf    OBJECT IDENTIFIER ::= { cevModuleUbrType 21 }
cevUbrMc28cBnc  OBJECT IDENTIFIER ::= { cevModuleUbrType 22 }
cevUbrMc26cf    OBJECT IDENTIFIER ::= { cevModuleUbrType 23 }
cevUbrMc26cBnc  OBJECT IDENTIFIER ::= { cevModuleUbrType 24 }
cevUbr905       OBJECT IDENTIFIER ::= { cevModuleUbrType 25 }
cevUbrDlc24     OBJECT IDENTIFIER ::= { cevModuleUbrType 26 }
cevModuleCmccType OBJECT IDENTIFIER ::= { cevModule 28 }
cevCmccCip      OBJECT IDENTIFIER ::= { cevModuleCmccType 1 }
cevCmccCip2     OBJECT IDENTIFIER ::= { cevModuleCmccType 2 }
cevCmccPa1ec    OBJECT IDENTIFIER ::= { cevModuleCmccType 3 }
cevCmccPa1pc    OBJECT IDENTIFIER ::= { cevModuleCmccType 4 }
cevCmccPa1ec4   OBJECT IDENTIFIER ::= { cevModuleCmccType 5 }
cevModuleCat6000Type OBJECT IDENTIFIER ::= { cevModule 29 }
cevCat6kWsxSup22ge OBJECT IDENTIFIER ::= { cevModuleCat6000Type 20 }
cevCat6kWsc6500SFM OBJECT IDENTIFIER ::= { cevModuleCat6000Type 21 }
cevCat6kWsc6500SFM2 OBJECT IDENTIFIER ::= { cevModuleCat6000Type 22 }
cevCat6kWsx6816GBIC OBJECT IDENTIFIER ::= { cevModuleCat6000Type 23 }
cevCat6kWsx6348RJ21 OBJECT IDENTIFIER ::= { cevModuleCat6000Type 28 }
cevCat6kWsx6516GBIC OBJECT IDENTIFIER ::= { cevModuleCat6000Type 29 }
cevCat6kWsxSup1a2ge OBJECT IDENTIFIER ::= { cevModuleCat6000Type 30 }
cevCat6kWsx6548RJ21 OBJECT IDENTIFIER ::= { cevModuleCat6000Type 31 }
cevCat6kWsx6416GEMT OBJECT IDENTIFIER ::= { cevModuleCat6000Type 32 }
cevCat6kWsx6380NAM OBJECT IDENTIFIER ::= { cevModuleCat6000Type 33 }
cevCat6kWsx6248aRJ45 OBJECT IDENTIFIER ::= { cevModuleCat6000Type 34 }
cevCat6kWsx6408aGbic OBJECT IDENTIFIER ::= { cevModuleCat6000Type 35 }
cevCat6kWsx6381IDS OBJECT IDENTIFIER ::= { cevModuleCat6000Type 36 }
cevCat6kWsx6524MmMT OBJECT IDENTIFIER ::= { cevModuleCat6000Type 37 }
cevCat6kIpSecVPNSm OBJECT IDENTIFIER ::= { cevModuleCat6000Type 49 }
cevModuleCat5000Type OBJECT IDENTIFIER ::= { cevModule 30 }
cevCat5kRsfc    OBJECT IDENTIFIER ::= { cevModuleCat5000Type 1 }
cevModule7100Type OBJECT IDENTIFIER ::= { cevModule 31 }
cevIo2feTxIsl   OBJECT IDENTIFIER ::= { cevModule7100Type 1 }
cevIsmIpsecMppe OBJECT IDENTIFIER ::= { cevModule7100Type 2 }
cev7100VPNAccelerator OBJECT IDENTIFIER ::= { cevModule7100Type 3 }
cev7100VPNAcceleratorModule2 OBJECT IDENTIFIER ::= { cevModule7100Type 4 }
cev7100VPNAcceleratorAES OBJECT IDENTIFIER ::= { cevModule7100Type 5 }
cevModule10000Type OBJECT IDENTIFIER ::= { cevModule 32 }
cevPos1oc12     OBJECT IDENTIFIER ::= { cevModule10000Type 1 }
cevP6Ct3        OBJECT IDENTIFIER ::= { cevModule10000Type 2 }
cevGe           OBJECT IDENTIFIER ::= { cevModule10000Type 3 }
cevAtm1Oc12     OBJECT IDENTIFIER ::= { cevModule10000Type 4 }
cevP1COc12      OBJECT IDENTIFIER ::= { cevModule10000Type 5 }
cevP4Chstm1     OBJECT IDENTIFIER ::= { cevModule10000Type 6 }
cev24feTx       OBJECT IDENTIFIER ::= { cevModule10000Type 8 }
cev24feFxMm     OBJECT IDENTIFIER ::= { cevModule10000Type 9 }
cev24feFxSm     OBJECT IDENTIFIER ::= { cevModule10000Type 10 }
cevSrpOc48SmSr  OBJECT IDENTIFIER ::= { cevModule10000Type 11 }
cevSrpOc48SmIr  OBJECT IDENTIFIER ::= { cevModule10000Type 12 }
cevPos6oc3      OBJECT IDENTIFIER ::= { cevModule10000Type 13 }
cevAtm4oc3      OBJECT IDENTIFIER ::= { cevModule10000Type 14 }
cevP8E3Ds3      OBJECT IDENTIFIER ::= { cevModule10000Type 15 }
cevC10K48MbFlashCard OBJECT IDENTIFIER ::= { cevModule10000Type 18 }
cevC10K128MbFlashCard OBJECT IDENTIFIER ::= { cevModule10000Type 19 }
cevP24ChE1T1    OBJECT IDENTIFIER ::= { cevModule10000Type 22 }
cevSrpOc48SmLr1 OBJECT IDENTIFIER ::= { cevModule10000Type 26 }
cevSrpOc48SmLr2 OBJECT IDENTIFIER ::= { cevModule10000Type 27 }
cevPosSrpOc48SmSr OBJECT IDENTIFIER ::= { cevModule10000Type 34 }
cevPosSrpOc48SmIr OBJECT IDENTIFIER ::= { cevModule10000Type 35 }
cevPosSrpOc48SmLr1 OBJECT IDENTIFIER ::= { cevModule10000Type 36 }
cevPosSrpOc48SmLr2 OBJECT IDENTIFIER ::= { cevModule10000Type 37 }
cevC10KJacket   OBJECT IDENTIFIER ::= { cevModule10000Type 38 }
cev24feTxB      OBJECT IDENTIFIER ::= { cevModule10000Type 39 }
cev4Ge8FeTxB    OBJECT IDENTIFIER ::= { cevModule10000Type 40 }
cevModuleAs5400Type OBJECT IDENTIFIER ::= { cevModule 33 }
cevAs5400DfcNp348 OBJECT IDENTIFIER ::= { cevModuleAs5400Type 2 }
cevAs5400DfcNp192 OBJECT IDENTIFIER ::= { cevModuleAs5400Type 3 }
cevModuleCat4000Type OBJECT IDENTIFIER ::= { cevModule 35 }
cevCat4232L3    OBJECT IDENTIFIER ::= { cevModuleCat4000Type 1 }
cevModuleCVAType OBJECT IDENTIFIER ::= { cevModule 36 }
cevCVA122       OBJECT IDENTIFIER ::= { cevModuleCVAType 1 }
cevCVA124       OBJECT IDENTIFIER ::= { cevModuleCVAType 2 }
cevCVA122E      OBJECT IDENTIFIER ::= { cevModuleCVAType 3 }
cevCVA124E      OBJECT IDENTIFIER ::= { cevModuleCVAType 4 }
cevModuleAs5850Type OBJECT IDENTIFIER ::= { cevModule 37 }
cevModule24xxType OBJECT IDENTIFIER ::= { cevModule 39 }
cevIad2420Vm8fxs OBJECT IDENTIFIER ::= { cevModule24xxType 1 }
cevIad242016fxs OBJECT IDENTIFIER ::= { cevModule24xxType 2 }
cevIad2420VmPwr OBJECT IDENTIFIER ::= { cevModule24xxType 3 }
cevIad2420Adsl  OBJECT IDENTIFIER ::= { cevModule24xxType 4 }
cevIad2420Hcm1  OBJECT IDENTIFIER ::= { cevModule24xxType 5 }
cevIad2420Hcm2  OBJECT IDENTIFIER ::= { cevModule24xxType 6 }
cevIad2420Hcm3  OBJECT IDENTIFIER ::= { cevModule24xxType 7 }
cevIad2420Hcm4  OBJECT IDENTIFIER ::= { cevModule24xxType 8 }
cevIad2420Hcm5  OBJECT IDENTIFIER ::= { cevModule24xxType 9 }
cevIad2420Hcm6  OBJECT IDENTIFIER ::= { cevModule24xxType 10 }
cevIad2420Cpu   OBJECT IDENTIFIER ::= { cevModule24xxType 11 }
cevIad2420MfmE1Unbalanced OBJECT IDENTIFIER ::= { cevModule24xxType 12 }
cevIad2420MfmE1Dsx1Csu OBJECT IDENTIFIER ::= { cevModule24xxType 13 }
cevIad2420MfmT1Dsx1Csu OBJECT IDENTIFIER ::= { cevModule24xxType 14 }
cevIad24208fxo  OBJECT IDENTIFIER ::= { cevModule24xxType 15 }
cevIad242016fxsOffPremise OBJECT IDENTIFIER ::= { cevModule24xxType 18 }
cevModuleONS15540Type OBJECT IDENTIFIER ::= { cevModule 42 }
cevONS15540LCMBTspProtect OBJECT IDENTIFIER ::= { cevModuleONS15540Type 1 }
cevONS15540LCMBTspEast OBJECT IDENTIFIER ::= { cevModuleONS15540Type 2 }
cevONS15540LCMBTspWest OBJECT IDENTIFIER ::= { cevModuleONS15540Type 3 }
cevONS15540MDXMBOSC OBJECT IDENTIFIER ::= { cevModuleONS15540Type 4 }
cevONS15540MDXMB OBJECT IDENTIFIER ::= { cevModuleONS15540Type 5 }
cevONS15540Tsp1Ch0102MmSc OBJECT IDENTIFIER ::= { cevModuleONS15540Type 6 }
cevONS15540Tsp1Ch0304MmSc OBJECT IDENTIFIER ::= { cevModuleONS15540Type 7 }
cevONS15540Tsp1Ch0506MmSc OBJECT IDENTIFIER ::= { cevModuleONS15540Type 8 }
cevONS15540Tsp1Ch0708MmSc OBJECT IDENTIFIER ::= { cevModuleONS15540Type 9 }
cevONS15540Tsp1Ch0910MmSc OBJECT IDENTIFIER ::= { cevModuleONS15540Type 10 }
cevONS15540Tsp1Ch1112MmSc OBJECT IDENTIFIER ::= { cevModuleONS15540Type 11 }
cevONS15540Tsp1Ch1314MmSc OBJECT IDENTIFIER ::= { cevModuleONS15540Type 12 }
cevONS15540Tsp1Ch1516MmSc OBJECT IDENTIFIER ::= { cevModuleONS15540Type 13 }
cevONS15540Tsp1Ch1718MmSc OBJECT IDENTIFIER ::= { cevModuleONS15540Type 14 }
cevONS15540Tsp1Ch1920MmSc OBJECT IDENTIFIER ::= { cevModuleONS15540Type 15 }
cevONS15540Tsp1Ch2122MmSc OBJECT IDENTIFIER ::= { cevModuleONS15540Type 16 }
cevONS15540Tsp1Ch2324MmSc OBJECT IDENTIFIER ::= { cevModuleONS15540Type 17 }
cevONS15540Tsp1Ch2526MmSc OBJECT IDENTIFIER ::= { cevModuleONS15540Type 18 }
cevONS15540Tsp1Ch2728MmSc OBJECT IDENTIFIER ::= { cevModuleONS15540Type 19 }
cevONS15540Tsp1Ch2930MmSc OBJECT IDENTIFIER ::= { cevModuleONS15540Type 20 }
cevONS15540Tsp1Ch3132MmSc OBJECT IDENTIFIER ::= { cevModuleONS15540Type 21 }
cevONS15540Tsp1Ch0102SmSc OBJECT IDENTIFIER ::= { cevModuleONS15540Type 22 }
cevONS15540Tsp1Ch0304SmSc OBJECT IDENTIFIER ::= { cevModuleONS15540Type 23 }
cevONS15540Tsp1Ch0506SmSc OBJECT IDENTIFIER ::= { cevModuleONS15540Type 24 }
cevONS15540Tsp1Ch0708SmSc OBJECT IDENTIFIER ::= { cevModuleONS15540Type 25 }
cevONS15540Tsp1Ch0910SmSc OBJECT IDENTIFIER ::= { cevModuleONS15540Type 26 }
cevONS15540Tsp1Ch1112SmSc OBJECT IDENTIFIER ::= { cevModuleONS15540Type 27 }
cevONS15540Tsp1Ch1314SmSc OBJECT IDENTIFIER ::= { cevModuleONS15540Type 28 }
cevONS15540Tsp1Ch1516SmSc OBJECT IDENTIFIER ::= { cevModuleONS15540Type 29 }
cevONS15540Tsp1Ch1718SmSc OBJECT IDENTIFIER ::= { cevModuleONS15540Type 30 }
cevONS15540Tsp1Ch1920SmSc OBJECT IDENTIFIER ::= { cevModuleONS15540Type 31 }
cevONS15540Tsp1Ch2122SmSc OBJECT IDENTIFIER ::= { cevModuleONS15540Type 32 }
cevONS15540Tsp1Ch2324SmSc OBJECT IDENTIFIER ::= { cevModuleONS15540Type 33 }
cevONS15540Tsp1Ch2526SmSc OBJECT IDENTIFIER ::= { cevModuleONS15540Type 34 }
cevONS15540Tsp1Ch2728SmSc OBJECT IDENTIFIER ::= { cevModuleONS15540Type 35 }
cevONS15540Tsp1Ch2930SmSc OBJECT IDENTIFIER ::= { cevModuleONS15540Type 36 }
cevONS15540Tsp1Ch3132SmSc OBJECT IDENTIFIER ::= { cevModuleONS15540Type 37 }
cevONS15540MDX4ChA OBJECT IDENTIFIER ::= { cevModuleONS15540Type 38 }
cevONS15540MDX4ChB OBJECT IDENTIFIER ::= { cevModuleONS15540Type 39 }
cevONS15540MDX4ChC OBJECT IDENTIFIER ::= { cevModuleONS15540Type 40 }
cevONS15540MDX4ChD OBJECT IDENTIFIER ::= { cevModuleONS15540Type 41 }
cevONS15540MDX4ChE OBJECT IDENTIFIER ::= { cevModuleONS15540Type 42 }
cevONS15540MDX4ChF OBJECT IDENTIFIER ::= { cevModuleONS15540Type 43 }
cevONS15540MDX4ChG OBJECT IDENTIFIER ::= { cevModuleONS15540Type 44 }
cevONS15540MDX4ChH OBJECT IDENTIFIER ::= { cevModuleONS15540Type 45 }
cevONS15540MDX8ChAB OBJECT IDENTIFIER ::= { cevModuleONS15540Type 46 }
cevONS15540MDX8ChCD OBJECT IDENTIFIER ::= { cevModuleONS15540Type 47 }
cevONS15540MDX8ChEF OBJECT IDENTIFIER ::= { cevModuleONS15540Type 48 }
cevONS15540MDX8ChGH OBJECT IDENTIFIER ::= { cevModuleONS15540Type 49 }
cevONS15540MDX4ChAOSC OBJECT IDENTIFIER ::= { cevModuleONS15540Type 50 }
cevONS15540MDX4ChBOSC OBJECT IDENTIFIER ::= { cevModuleONS15540Type 51 }
cevONS15540MDX4ChCOSC OBJECT IDENTIFIER ::= { cevModuleONS15540Type 52 }
cevONS15540MDX4ChDOSC OBJECT IDENTIFIER ::= { cevModuleONS15540Type 53 }
cevONS15540MDX4ChEOSC OBJECT IDENTIFIER ::= { cevModuleONS15540Type 54 }
cevONS15540MDX4ChFOSC OBJECT IDENTIFIER ::= { cevModuleONS15540Type 55 }
cevONS15540MDX4ChGOSC OBJECT IDENTIFIER ::= { cevModuleONS15540Type 56 }
cevONS15540MDX4ChHOSC OBJECT IDENTIFIER ::= { cevModuleONS15540Type 57 }
cevONS15540MDX8ChABOSC OBJECT IDENTIFIER ::= { cevModuleONS15540Type 58 }
cevONS15540MDX8ChCDOSC OBJECT IDENTIFIER ::= { cevModuleONS15540Type 59 }
cevONS15540MDX8ChEFOSC OBJECT IDENTIFIER ::= { cevModuleONS15540Type 60 }
cevONS15540MDX8ChGHOSC OBJECT IDENTIFIER ::= { cevModuleONS15540Type 61 }
cevONS15540MDX16ChADOSC OBJECT IDENTIFIER ::= { cevModuleONS15540Type 62 }
cevONS15540MDX16ChEH OBJECT IDENTIFIER ::= { cevModuleONS15540Type 63 }
cevONS15540Tsp2Ch0102 OBJECT IDENTIFIER ::= { cevModuleONS15540Type 64 }
cevONS15540Tsp2Ch0304 OBJECT IDENTIFIER ::= { cevModuleONS15540Type 65 }
cevONS15540Tsp2Ch0506 OBJECT IDENTIFIER ::= { cevModuleONS15540Type 66 }
cevONS15540Tsp2Ch0708 OBJECT IDENTIFIER ::= { cevModuleONS15540Type 67 }
cevONS15540Tsp2Ch0910 OBJECT IDENTIFIER ::= { cevModuleONS15540Type 68 }
cevONS15540Tsp2Ch1112 OBJECT IDENTIFIER ::= { cevModuleONS15540Type 69 }
cevONS15540Tsp2Ch1314 OBJECT IDENTIFIER ::= { cevModuleONS15540Type 70 }
cevONS15540Tsp2Ch1516 OBJECT IDENTIFIER ::= { cevModuleONS15540Type 71 }
cevONS15540Tsp2Ch1718 OBJECT IDENTIFIER ::= { cevModuleONS15540Type 72 }
cevONS15540Tsp2Ch1920 OBJECT IDENTIFIER ::= { cevModuleONS15540Type 73 }
cevONS15540Tsp2Ch2122 OBJECT IDENTIFIER ::= { cevModuleONS15540Type 74 }
cevONS15540Tsp2Ch2324 OBJECT IDENTIFIER ::= { cevModuleONS15540Type 75 }
cevONS15540Tsp2Ch2526 OBJECT IDENTIFIER ::= { cevModuleONS15540Type 76 }
cevONS15540Tsp2Ch2728 OBJECT IDENTIFIER ::= { cevModuleONS15540Type 77 }
cevONS15540Tsp2Ch2930 OBJECT IDENTIFIER ::= { cevModuleONS15540Type 78 }
cevONS15540Tsp2Ch3132 OBJECT IDENTIFIER ::= { cevModuleONS15540Type 79 }
cevONS15540LCMB10GOC192c OBJECT IDENTIFIER ::= { cevModuleONS15540Type 80 }
cevONS15540ESPxLCMBTspSp OBJECT IDENTIFIER ::= { cevModuleONS15540Type 81 }
cevONS15540ESPxLCMBTsp OBJECT IDENTIFIER ::= { cevModuleONS15540Type 82 }
cevONS15540ESPxLCMB10GOC192cSp OBJECT IDENTIFIER ::= { cevModuleONS15540Type 83 }
cevONS15540ESPxLCMB10GOC192c OBJECT IDENTIFIER ::= { cevModuleONS15540Type 84 }
cevONS15540LCDC10G OBJECT IDENTIFIER ::= { cevModuleONS15540Type 85 }
cevONS15540ESPxMDXMBOsc OBJECT IDENTIFIER ::= { cevModuleONS15540Type 86 }
cevONS15540ESPxMDXMB OBJECT IDENTIFIER ::= { cevModuleONS15540Type 87 }
cevONS15540ESPxMDXMBOscESP OBJECT IDENTIFIER ::= { cevModuleONS15540Type 88 }
cevONS15540ESPxMDXMBESP OBJECT IDENTIFIER ::= { cevModuleONS15540Type 89 }
cevONS1554010GigITUCh01 OBJECT IDENTIFIER ::= { cevModuleONS15540Type 90 }
cevONS1554010GigITUCh02 OBJECT IDENTIFIER ::= { cevModuleONS15540Type 91 }
cevONS1554010GigITUCh03 OBJECT IDENTIFIER ::= { cevModuleONS15540Type 92 }
cevONS1554010GigITUCh04 OBJECT IDENTIFIER ::= { cevModuleONS15540Type 93 }
cevONS1554010GigITUCh05 OBJECT IDENTIFIER ::= { cevModuleONS15540Type 94 }
cevONS1554010GigITUCh06 OBJECT IDENTIFIER ::= { cevModuleONS15540Type 95 }
cevONS1554010GigITUCh07 OBJECT IDENTIFIER ::= { cevModuleONS15540Type 96 }
cevONS1554010GigITUCh08 OBJECT IDENTIFIER ::= { cevModuleONS15540Type 97 }
cevONS1554010GigITUCh09 OBJECT IDENTIFIER ::= { cevModuleONS15540Type 98 }
cevONS1554010GigITUCh10 OBJECT IDENTIFIER ::= { cevModuleONS15540Type 99 }
cevONS1554010GigITUCh11 OBJECT IDENTIFIER ::= { cevModuleONS15540Type 100 }
cevONS1554010GigITUCh12 OBJECT IDENTIFIER ::= { cevModuleONS15540Type 101 }
cevONS1554010GigITUCh13 OBJECT IDENTIFIER ::= { cevModuleONS15540Type 102 }
cevONS1554010GigITUCh14 OBJECT IDENTIFIER ::= { cevModuleONS15540Type 103 }
cevONS1554010GigITUCh15 OBJECT IDENTIFIER ::= { cevModuleONS15540Type 104 }
cevONS1554010GigITUCh16 OBJECT IDENTIFIER ::= { cevModuleONS15540Type 105 }
cevONS1554010GigITUCh17 OBJECT IDENTIFIER ::= { cevModuleONS15540Type 106 }
cevONS1554010GigITUCh18 OBJECT IDENTIFIER ::= { cevModuleONS15540Type 107 }
cevONS1554010GigITUCh19 OBJECT IDENTIFIER ::= { cevModuleONS15540Type 108 }
cevONS1554010GigITUCh20 OBJECT IDENTIFIER ::= { cevModuleONS15540Type 109 }
cevONS1554010GigITUCh21 OBJECT IDENTIFIER ::= { cevModuleONS15540Type 110 }
cevONS1554010GigITUCh22 OBJECT IDENTIFIER ::= { cevModuleONS15540Type 111 }
cevONS1554010GigITUCh23 OBJECT IDENTIFIER ::= { cevModuleONS15540Type 112 }
cevONS1554010GigITUCh24 OBJECT IDENTIFIER ::= { cevModuleONS15540Type 113 }
cevONS1554010GigITUCh25 OBJECT IDENTIFIER ::= { cevModuleONS15540Type 114 }
cevONS1554010GigITUCh26 OBJECT IDENTIFIER ::= { cevModuleONS15540Type 115 }
cevONS1554010GigITUCh27 OBJECT IDENTIFIER ::= { cevModuleONS15540Type 116 }
cevONS1554010GigITUCh28 OBJECT IDENTIFIER ::= { cevModuleONS15540Type 117 }
cevONS1554010GigITUCh29 OBJECT IDENTIFIER ::= { cevModuleONS15540Type 118 }
cevONS1554010GigITUCh30 OBJECT IDENTIFIER ::= { cevModuleONS15540Type 119 }
cevONS1554010GigITUCh31 OBJECT IDENTIFIER ::= { cevModuleONS15540Type 120 }
cevONS1554010GigITUCh32 OBJECT IDENTIFIER ::= { cevModuleONS15540Type 121 }
cevONS15540OC192cITUCh01 OBJECT IDENTIFIER ::= { cevModuleONS15540Type 122 }
cevONS15540OC192cITUCh02 OBJECT IDENTIFIER ::= { cevModuleONS15540Type 123 }
cevONS15540OC192cITUCh03 OBJECT IDENTIFIER ::= { cevModuleONS15540Type 124 }
cevONS15540OC192cITUCh04 OBJECT IDENTIFIER ::= { cevModuleONS15540Type 125 }
cevONS15540OC192cITUCh05 OBJECT IDENTIFIER ::= { cevModuleONS15540Type 126 }
cevONS15540OC192cITUCh06 OBJECT IDENTIFIER ::= { cevModuleONS15540Type 127 }
cevONS15540OC192cITUCh07 OBJECT IDENTIFIER ::= { cevModuleONS15540Type 128 }
cevONS15540OC192cITUCh08 OBJECT IDENTIFIER ::= { cevModuleONS15540Type 129 }
cevONS15540OC192cITUCh09 OBJECT IDENTIFIER ::= { cevModuleONS15540Type 130 }
cevONS15540OC192cITUCh10 OBJECT IDENTIFIER ::= { cevModuleONS15540Type 131 }
cevONS15540OC192cITUCh11 OBJECT IDENTIFIER ::= { cevModuleONS15540Type 132 }
cevONS15540OC192cITUCh12 OBJECT IDENTIFIER ::= { cevModuleONS15540Type 133 }
cevONS15540OC192cITUCh13 OBJECT IDENTIFIER ::= { cevModuleONS15540Type 134 }
cevONS15540OC192cITUCh14 OBJECT IDENTIFIER ::= { cevModuleONS15540Type 135 }
cevONS15540OC192cITUCh15 OBJECT IDENTIFIER ::= { cevModuleONS15540Type 136 }
cevONS15540OC192cITUCh16 OBJECT IDENTIFIER ::= { cevModuleONS15540Type 137 }
cevONS15540OC192cITUCh17 OBJECT IDENTIFIER ::= { cevModuleONS15540Type 138 }
cevONS15540OC192cITUCh18 OBJECT IDENTIFIER ::= { cevModuleONS15540Type 139 }
cevONS15540OC192cITUCh19 OBJECT IDENTIFIER ::= { cevModuleONS15540Type 140 }
cevONS15540OC192cITUCh20 OBJECT IDENTIFIER ::= { cevModuleONS15540Type 141 }
cevONS15540OC192cITUCh21 OBJECT IDENTIFIER ::= { cevModuleONS15540Type 142 }
cevONS15540OC192cITUCh22 OBJECT IDENTIFIER ::= { cevModuleONS15540Type 143 }
cevONS15540OC192cITUCh23 OBJECT IDENTIFIER ::= { cevModuleONS15540Type 144 }
cevONS15540OC192cITUCh24 OBJECT IDENTIFIER ::= { cevModuleONS15540Type 145 }
cevONS15540OC192cITUCh25 OBJECT IDENTIFIER ::= { cevModuleONS15540Type 146 }
cevONS15540OC192cITUCh26 OBJECT IDENTIFIER ::= { cevModuleONS15540Type 147 }
cevONS15540OC192cITUCh27 OBJECT IDENTIFIER ::= { cevModuleONS15540Type 148 }
cevONS15540OC192cITUCh28 OBJECT IDENTIFIER ::= { cevModuleONS15540Type 149 }
cevONS15540OC192cITUCh29 OBJECT IDENTIFIER ::= { cevModuleONS15540Type 150 }
cevONS15540OC192cITUCh30 OBJECT IDENTIFIER ::= { cevModuleONS15540Type 151 }
cevONS15540OC192cITUCh31 OBJECT IDENTIFIER ::= { cevModuleONS15540Type 152 }
cevONS15540OC192cITUCh32 OBJECT IDENTIFIER ::= { cevModuleONS15540Type 153 }
cevONS15540ESPxMDX4ChA OBJECT IDENTIFIER ::= { cevModuleONS15540Type 154 }
cevONS15540ESPxMDX4ChB OBJECT IDENTIFIER ::= { cevModuleONS15540Type 155 }
cevONS15540ESPxMDX4ChC OBJECT IDENTIFIER ::= { cevModuleONS15540Type 156 }
cevONS15540ESPxMDX4ChD OBJECT IDENTIFIER ::= { cevModuleONS15540Type 157 }
cevONS15540ESPxMDX4ChE OBJECT IDENTIFIER ::= { cevModuleONS15540Type 158 }
cevONS15540ESPxMDX4ChF OBJECT IDENTIFIER ::= { cevModuleONS15540Type 159 }
cevONS15540ESPxMDX4ChG OBJECT IDENTIFIER ::= { cevModuleONS15540Type 160 }
cevONS15540ESPxMDX4ChH OBJECT IDENTIFIER ::= { cevModuleONS15540Type 161 }
cevONS15540ESPxMDX8ChAB OBJECT IDENTIFIER ::= { cevModuleONS15540Type 162 }
cevONS15540ESPxMDX8ChCD OBJECT IDENTIFIER ::= { cevModuleONS15540Type 163 }
cevONS15540ESPxMDX8ChEF OBJECT IDENTIFIER ::= { cevModuleONS15540Type 164 }
cevONS15540ESPxMDX8ChGH OBJECT IDENTIFIER ::= { cevModuleONS15540Type 165 }
cevONS15540ESPxMDX16ChEH OBJECT IDENTIFIER ::= { cevModuleONS15540Type 166 }
cevONS15540ESPxMDX4ChAOSC OBJECT IDENTIFIER ::= { cevModuleONS15540Type 167 }
cevONS15540ESPxMDX4ChBOSC OBJECT IDENTIFIER ::= { cevModuleONS15540Type 168 }
cevONS15540ESPxMDX4ChCOSC OBJECT IDENTIFIER ::= { cevModuleONS15540Type 169 }
cevONS15540ESPxMDX4ChDOSC OBJECT IDENTIFIER ::= { cevModuleONS15540Type 170 }
cevONS15540ESPxMDX4ChEOSC OBJECT IDENTIFIER ::= { cevModuleONS15540Type 171 }
cevONS15540ESPxMDX4ChFOSC OBJECT IDENTIFIER ::= { cevModuleONS15540Type 172 }
cevONS15540ESPxMDX4ChGOSC OBJECT IDENTIFIER ::= { cevModuleONS15540Type 173 }
cevONS15540ESPxMDX4ChHOSC OBJECT IDENTIFIER ::= { cevModuleONS15540Type 174 }
cevONS15540ESPxMDX8ChABOSC OBJECT IDENTIFIER ::= { cevModuleONS15540Type 175 }
cevONS15540ESPxMDX8ChCDOSC OBJECT IDENTIFIER ::= { cevModuleONS15540Type 176 }
cevONS15540ESPxMDX8ChEFOSC OBJECT IDENTIFIER ::= { cevModuleONS15540Type 177 }
cevONS15540ESPxMDX8ChGHOSC OBJECT IDENTIFIER ::= { cevModuleONS15540Type 178 }
cevONS15540ESPxMDX16ChADOSC OBJECT IDENTIFIER ::= { cevModuleONS15540Type 179 }
cevONS15540ESPxMDX32ChOSC OBJECT IDENTIFIER ::= { cevModuleONS15540Type 180 }
cevONS15540EspPxPSM OBJECT IDENTIFIER ::= { cevModuleONS15540Type 181 }
cevModuleGsrPortAdapterType OBJECT IDENTIFIER ::= { cevModule 43 }
cevGsrPaUnknown OBJECT IDENTIFIER ::= { cevModuleGsrPortAdapterType 1 }
cevGsrPa1Ge     OBJECT IDENTIFIER ::= { cevModuleGsrPortAdapterType 2 }
cevGsrPa3Ge     OBJECT IDENTIFIER ::= { cevModuleGsrPortAdapterType 3 }
cevGsrPa24Fe    OBJECT IDENTIFIER ::= { cevModuleGsrPortAdapterType 4 }
cevModuleONS15530Type OBJECT IDENTIFIER ::= { cevModule 44 }
cevONS15530LCMBOsc OBJECT IDENTIFIER ::= { cevModuleONS15530Type 1 }
cevONS15530Osc  OBJECT IDENTIFIER ::= { cevModuleONS15530Type 2 }
cevONS15530MDX4ChA OBJECT IDENTIFIER ::= { cevModuleONS15530Type 3 }
cevONS15530MDX4ChB OBJECT IDENTIFIER ::= { cevModuleONS15530Type 4 }
cevONS15530MDX4ChC OBJECT IDENTIFIER ::= { cevModuleONS15530Type 5 }
cevONS15530MDX4ChD OBJECT IDENTIFIER ::= { cevModuleONS15530Type 6 }
cevONS15530MDX4ChE OBJECT IDENTIFIER ::= { cevModuleONS15530Type 7 }
cevONS15530MDX4ChF OBJECT IDENTIFIER ::= { cevModuleONS15530Type 8 }
cevONS15530MDX4ChG OBJECT IDENTIFIER ::= { cevModuleONS15530Type 9 }
cevONS15530MDX4ChH OBJECT IDENTIFIER ::= { cevModuleONS15530Type 10 }
cevONS15530MDX4ChAOsc OBJECT IDENTIFIER ::= { cevModuleONS15530Type 11 }
cevONS15530MDX4ChBOsc OBJECT IDENTIFIER ::= { cevModuleONS15530Type 12 }
cevONS15530MDX4ChCOsc OBJECT IDENTIFIER ::= { cevModuleONS15530Type 13 }
cevONS15530MDX4ChDOsc OBJECT IDENTIFIER ::= { cevModuleONS15530Type 14 }
cevONS15530MDX4ChEOsc OBJECT IDENTIFIER ::= { cevModuleONS15530Type 15 }
cevONS15530MDX4ChFOsc OBJECT IDENTIFIER ::= { cevModuleONS15530Type 16 }
cevONS15530MDX4ChGOsc OBJECT IDENTIFIER ::= { cevModuleONS15530Type 17 }
cevONS15530MDX4ChHOsc OBJECT IDENTIFIER ::= { cevModuleONS15530Type 18 }
cevONS15530Tsp1Ch0102MmScSp OBJECT IDENTIFIER ::= { cevModuleONS15530Type 19 }
cevONS15530Tsp1Ch0304MmScSp OBJECT IDENTIFIER ::= { cevModuleONS15530Type 20 }
cevONS15530Tsp1Ch0506MmScSp OBJECT IDENTIFIER ::= { cevModuleONS15530Type 21 }
cevONS15530Tsp1Ch0708MmScSp OBJECT IDENTIFIER ::= { cevModuleONS15530Type 22 }
cevONS15530Tsp1Ch0910MmScSp OBJECT IDENTIFIER ::= { cevModuleONS15530Type 23 }
cevONS15530Tsp1Ch1112MmScSp OBJECT IDENTIFIER ::= { cevModuleONS15530Type 24 }
cevONS15530Tsp1Ch1314MmScSp OBJECT IDENTIFIER ::= { cevModuleONS15530Type 25 }
cevONS15530Tsp1Ch1516MmScSp OBJECT IDENTIFIER ::= { cevModuleONS15530Type 26 }
cevONS15530Tsp1Ch1718MmScSp OBJECT IDENTIFIER ::= { cevModuleONS15530Type 27 }
cevONS15530Tsp1Ch1920MmScSp OBJECT IDENTIFIER ::= { cevModuleONS15530Type 28 }
cevONS15530Tsp1Ch2122MmScSp OBJECT IDENTIFIER ::= { cevModuleONS15530Type 29 }
cevONS15530Tsp1Ch2324MmScSp OBJECT IDENTIFIER ::= { cevModuleONS15530Type 30 }
cevONS15530Tsp1Ch2526MmScSp OBJECT IDENTIFIER ::= { cevModuleONS15530Type 31 }
cevONS15530Tsp1Ch2728MmScSp OBJECT IDENTIFIER ::= { cevModuleONS15530Type 32 }
cevONS15530Tsp1Ch2930MmScSp OBJECT IDENTIFIER ::= { cevModuleONS15530Type 33 }
cevONS15530Tsp1Ch3132MmScSp OBJECT IDENTIFIER ::= { cevModuleONS15530Type 34 }
cevONS15530Tsp1Ch0102SmScSp OBJECT IDENTIFIER ::= { cevModuleONS15530Type 35 }
cevONS15530Tsp1Ch0304SmScSp OBJECT IDENTIFIER ::= { cevModuleONS15530Type 36 }
cevONS15530Tsp1Ch0506SmScSp OBJECT IDENTIFIER ::= { cevModuleONS15530Type 37 }
cevONS15530Tsp1Ch0708SmScSp OBJECT IDENTIFIER ::= { cevModuleONS15530Type 38 }
cevONS15530Tsp1Ch0910SmScSp OBJECT IDENTIFIER ::= { cevModuleONS15530Type 39 }
cevONS15530Tsp1Ch1112SmScSp OBJECT IDENTIFIER ::= { cevModuleONS15530Type 40 }
cevONS15530Tsp1Ch1314SmScSp OBJECT IDENTIFIER ::= { cevModuleONS15530Type 41 }
cevONS15530Tsp1Ch1516SmScSp OBJECT IDENTIFIER ::= { cevModuleONS15530Type 42 }
cevONS15530Tsp1Ch1718SmScSp OBJECT IDENTIFIER ::= { cevModuleONS15530Type 43 }
cevONS15530Tsp1Ch1920SmScSp OBJECT IDENTIFIER ::= { cevModuleONS15530Type 44 }
cevONS15530Tsp1Ch2122SmScSp OBJECT IDENTIFIER ::= { cevModuleONS15530Type 45 }
cevONS15530Tsp1Ch2324SmScSp OBJECT IDENTIFIER ::= { cevModuleONS15530Type 46 }
cevONS15530Tsp1Ch2526SmScSp OBJECT IDENTIFIER ::= { cevModuleONS15530Type 47 }
cevONS15530Tsp1Ch2728SmScSp OBJECT IDENTIFIER ::= { cevModuleONS15530Type 48 }
cevONS15530Tsp1Ch2930SmScSp OBJECT IDENTIFIER ::= { cevModuleONS15530Type 49 }
cevONS15530Tsp1Ch3132SmScSp OBJECT IDENTIFIER ::= { cevModuleONS15530Type 50 }
cevONS15530Tsp1Ch0102MmSc OBJECT IDENTIFIER ::= { cevModuleONS15530Type 51 }
cevONS15530Tsp1Ch0304MmSc OBJECT IDENTIFIER ::= { cevModuleONS15530Type 52 }
cevONS15530Tsp1Ch0506MmSc OBJECT IDENTIFIER ::= { cevModuleONS15530Type 53 }
cevONS15530Tsp1Ch0708MmSc OBJECT IDENTIFIER ::= { cevModuleONS15530Type 54 }
cevONS15530Tsp1Ch0910MmSc OBJECT IDENTIFIER ::= { cevModuleONS15530Type 55 }
cevONS15530Tsp1Ch1112MmSc OBJECT IDENTIFIER ::= { cevModuleONS15530Type 56 }
cevONS15530Tsp1Ch1314MmSc OBJECT IDENTIFIER ::= { cevModuleONS15530Type 57 }
cevONS15530Tsp1Ch1516MmSc OBJECT IDENTIFIER ::= { cevModuleONS15530Type 58 }
cevONS15530Tsp1Ch1718MmSc OBJECT IDENTIFIER ::= { cevModuleONS15530Type 59 }
cevONS15530Tsp1Ch1920MmSc OBJECT IDENTIFIER ::= { cevModuleONS15530Type 60 }
cevONS15530Tsp1Ch2122MmSc OBJECT IDENTIFIER ::= { cevModuleONS15530Type 61 }
cevONS15530Tsp1Ch2324MmSc OBJECT IDENTIFIER ::= { cevModuleONS15530Type 62 }
cevONS15530Tsp1Ch2526MmSc OBJECT IDENTIFIER ::= { cevModuleONS15530Type 63 }
cevONS15530Tsp1Ch2728MmSc OBJECT IDENTIFIER ::= { cevModuleONS15530Type 64 }
cevONS15530Tsp1Ch2930MmSc OBJECT IDENTIFIER ::= { cevModuleONS15530Type 65 }
cevONS15530Tsp1Ch3132MmSc OBJECT IDENTIFIER ::= { cevModuleONS15530Type 66 }
cevONS15530Tsp1Ch0102SmSc OBJECT IDENTIFIER ::= { cevModuleONS15530Type 67 }
cevONS15530Tsp1Ch0304SmSc OBJECT IDENTIFIER ::= { cevModuleONS15530Type 68 }
cevONS15530Tsp1Ch0506SmSc OBJECT IDENTIFIER ::= { cevModuleONS15530Type 69 }
cevONS15530Tsp1Ch0708SmSc OBJECT IDENTIFIER ::= { cevModuleONS15530Type 70 }
cevONS15530Tsp1Ch0910SmSc OBJECT IDENTIFIER ::= { cevModuleONS15530Type 71 }
cevONS15530Tsp1Ch1112SmSc OBJECT IDENTIFIER ::= { cevModuleONS15530Type 72 }
cevONS15530Tsp1Ch1314SmSc OBJECT IDENTIFIER ::= { cevModuleONS15530Type 73 }
cevONS15530Tsp1Ch1516SmSc OBJECT IDENTIFIER ::= { cevModuleONS15530Type 74 }
cevONS15530Tsp1Ch1718SmSc OBJECT IDENTIFIER ::= { cevModuleONS15530Type 75 }
cevONS15530Tsp1Ch1920SmSc OBJECT IDENTIFIER ::= { cevModuleONS15530Type 76 }
cevONS15530Tsp1Ch2122SmSc OBJECT IDENTIFIER ::= { cevModuleONS15530Type 77 }
cevONS15530Tsp1Ch2324SmSc OBJECT IDENTIFIER ::= { cevModuleONS15530Type 78 }
cevONS15530Tsp1Ch2526SmSc OBJECT IDENTIFIER ::= { cevModuleONS15530Type 79 }
cevONS15530Tsp1Ch2728SmSc OBJECT IDENTIFIER ::= { cevModuleONS15530Type 80 }
cevONS15530Tsp1Ch2930SmSc OBJECT IDENTIFIER ::= { cevModuleONS15530Type 81 }
cevONS15530Tsp1Ch3132SmSc OBJECT IDENTIFIER ::= { cevModuleONS15530Type 82 }
cevONS15530LCEscon10 OBJECT IDENTIFIER ::= { cevModuleONS15530Type 83 }
cevONS15500XvrEscon1310MmMTRJ OBJECT IDENTIFIER ::= { cevModuleONS15530Type 84 }
cevONS15530LC10GESmSc OBJECT IDENTIFIER ::= { cevModuleONS15530Type 85 }
cevONS1553010GCh01Sp OBJECT IDENTIFIER ::= { cevModuleONS15530Type 86 }
cevONS1553010GCh02Sp OBJECT IDENTIFIER ::= { cevModuleONS15530Type 87 }
cevONS1553010GCh03Sp OBJECT IDENTIFIER ::= { cevModuleONS15530Type 88 }
cevONS1553010GCh04Sp OBJECT IDENTIFIER ::= { cevModuleONS15530Type 89 }
cevONS1553010GCh05Sp OBJECT IDENTIFIER ::= { cevModuleONS15530Type 90 }
cevONS1553010GCh06Sp OBJECT IDENTIFIER ::= { cevModuleONS15530Type 91 }
cevONS1553010GCh07Sp OBJECT IDENTIFIER ::= { cevModuleONS15530Type 92 }
cevONS1553010GCh08Sp OBJECT IDENTIFIER ::= { cevModuleONS15530Type 93 }
cevONS1553010GCh09Sp OBJECT IDENTIFIER ::= { cevModuleONS15530Type 94 }
cevONS1553010GCh10Sp OBJECT IDENTIFIER ::= { cevModuleONS15530Type 95 }
cevONS1553010GCh11Sp OBJECT IDENTIFIER ::= { cevModuleONS15530Type 96 }
cevONS1553010GCh12Sp OBJECT IDENTIFIER ::= { cevModuleONS15530Type 97 }
cevONS1553010GCh13Sp OBJECT IDENTIFIER ::= { cevModuleONS15530Type 98 }
cevONS1553010GCh14Sp OBJECT IDENTIFIER ::= { cevModuleONS15530Type 99 }
cevONS1553010GCh15Sp OBJECT IDENTIFIER ::= { cevModuleONS15530Type 100 }
cevONS1553010GCh16Sp OBJECT IDENTIFIER ::= { cevModuleONS15530Type 101 }
cevONS1553010GCh17Sp OBJECT IDENTIFIER ::= { cevModuleONS15530Type 102 }
cevONS1553010GCh18Sp OBJECT IDENTIFIER ::= { cevModuleONS15530Type 103 }
cevONS1553010GCh19Sp OBJECT IDENTIFIER ::= { cevModuleONS15530Type 104 }
cevONS1553010GCh20Sp OBJECT IDENTIFIER ::= { cevModuleONS15530Type 105 }
cevONS1553010GCh21Sp OBJECT IDENTIFIER ::= { cevModuleONS15530Type 106 }
cevONS1553010GCh22Sp OBJECT IDENTIFIER ::= { cevModuleONS15530Type 107 }
cevONS1553010GCh23Sp OBJECT IDENTIFIER ::= { cevModuleONS15530Type 108 }
cevONS1553010GCh24Sp OBJECT IDENTIFIER ::= { cevModuleONS15530Type 109 }
cevONS1553010GCh25Sp OBJECT IDENTIFIER ::= { cevModuleONS15530Type 110 }
cevONS1553010GCh26Sp OBJECT IDENTIFIER ::= { cevModuleONS15530Type 111 }
cevONS1553010GCh27Sp OBJECT IDENTIFIER ::= { cevModuleONS15530Type 112 }
cevONS1553010GCh28Sp OBJECT IDENTIFIER ::= { cevModuleONS15530Type 113 }
cevONS1553010GCh29Sp OBJECT IDENTIFIER ::= { cevModuleONS15530Type 114 }
cevONS1553010GCh30Sp OBJECT IDENTIFIER ::= { cevModuleONS15530Type 115 }
cevONS1553010GCh31Sp OBJECT IDENTIFIER ::= { cevModuleONS15530Type 116 }
cevONS1553010GCh32Sp OBJECT IDENTIFIER ::= { cevModuleONS15530Type 117 }
cevONS1553010GCh01 OBJECT IDENTIFIER ::= { cevModuleONS15530Type 118 }
cevONS1553010GCh02 OBJECT IDENTIFIER ::= { cevModuleONS15530Type 119 }
cevONS1553010GCh03 OBJECT IDENTIFIER ::= { cevModuleONS15530Type 120 }
cevONS1553010GCh04 OBJECT IDENTIFIER ::= { cevModuleONS15530Type 121 }
cevONS1553010GCh05 OBJECT IDENTIFIER ::= { cevModuleONS15530Type 122 }
cevONS1553010GCh06 OBJECT IDENTIFIER ::= { cevModuleONS15530Type 123 }
cevONS1553010GCh07 OBJECT IDENTIFIER ::= { cevModuleONS15530Type 124 }
cevONS1553010GCh08 OBJECT IDENTIFIER ::= { cevModuleONS15530Type 125 }
cevONS1553010GCh09 OBJECT IDENTIFIER ::= { cevModuleONS15530Type 126 }
cevONS1553010GCh10 OBJECT IDENTIFIER ::= { cevModuleONS15530Type 127 }
cevONS1553010GCh11 OBJECT IDENTIFIER ::= { cevModuleONS15530Type 128 }
cevONS1553010GCh12 OBJECT IDENTIFIER ::= { cevModuleONS15530Type 129 }
cevONS1553010GCh13 OBJECT IDENTIFIER ::= { cevModuleONS15530Type 130 }
cevONS1553010GCh14 OBJECT IDENTIFIER ::= { cevModuleONS15530Type 131 }
cevONS1553010GCh15 OBJECT IDENTIFIER ::= { cevModuleONS15530Type 132 }
cevONS1553010GCh16 OBJECT IDENTIFIER ::= { cevModuleONS15530Type 133 }
cevONS1553010GCh17 OBJECT IDENTIFIER ::= { cevModuleONS15530Type 134 }
cevONS1553010GCh18 OBJECT IDENTIFIER ::= { cevModuleONS15530Type 135 }
cevONS1553010GCh19 OBJECT IDENTIFIER ::= { cevModuleONS15530Type 136 }
cevONS1553010GCh20 OBJECT IDENTIFIER ::= { cevModuleONS15530Type 137 }
cevONS1553010GCh21 OBJECT IDENTIFIER ::= { cevModuleONS15530Type 138 }
cevONS1553010GCh22 OBJECT IDENTIFIER ::= { cevModuleONS15530Type 139 }
cevONS1553010GCh23 OBJECT IDENTIFIER ::= { cevModuleONS15530Type 140 }
cevONS1553010GCh24 OBJECT IDENTIFIER ::= { cevModuleONS15530Type 141 }
cevONS1553010GCh25 OBJECT IDENTIFIER ::= { cevModuleONS15530Type 142 }
cevONS1553010GCh26 OBJECT IDENTIFIER ::= { cevModuleONS15530Type 143 }
cevONS1553010GCh27 OBJECT IDENTIFIER ::= { cevModuleONS15530Type 144 }
cevONS1553010GCh28 OBJECT IDENTIFIER ::= { cevModuleONS15530Type 145 }
cevONS1553010GCh29 OBJECT IDENTIFIER ::= { cevModuleONS15530Type 146 }
cevONS1553010GCh30 OBJECT IDENTIFIER ::= { cevModuleONS15530Type 147 }
cevONS1553010GCh31 OBJECT IDENTIFIER ::= { cevModuleONS15530Type 148 }
cevONS1553010GCh32 OBJECT IDENTIFIER ::= { cevModuleONS15530Type 149 }
cevONS15530FCGE8P OBJECT IDENTIFIER ::= { cevModuleONS15530Type 150 }
cevONS155302p5GCh0102Sp OBJECT IDENTIFIER ::= { cevModuleONS15530Type 151 }
cevONS155302p5GCh0304Sp OBJECT IDENTIFIER ::= { cevModuleONS15530Type 152 }
cevONS155302p5GCh0506Sp OBJECT IDENTIFIER ::= { cevModuleONS15530Type 153 }
cevONS155302p5GCh0708Sp OBJECT IDENTIFIER ::= { cevModuleONS15530Type 154 }
cevONS155302p5GCh0910Sp OBJECT IDENTIFIER ::= { cevModuleONS15530Type 155 }
cevONS155302p5GCh1112Sp OBJECT IDENTIFIER ::= { cevModuleONS15530Type 156 }
cevONS155302p5GCh1314Sp OBJECT IDENTIFIER ::= { cevModuleONS15530Type 157 }
cevONS155302p5GCh1516Sp OBJECT IDENTIFIER ::= { cevModuleONS15530Type 158 }
cevONS155302p5GCh1718Sp OBJECT IDENTIFIER ::= { cevModuleONS15530Type 159 }
cevONS155302p5GCh1920Sp OBJECT IDENTIFIER ::= { cevModuleONS15530Type 160 }
cevONS155302p5GCh2122Sp OBJECT IDENTIFIER ::= { cevModuleONS15530Type 161 }
cevONS155302p5GCh2324Sp OBJECT IDENTIFIER ::= { cevModuleONS15530Type 162 }
cevONS155302p5GCh2526Sp OBJECT IDENTIFIER ::= { cevModuleONS15530Type 163 }
cevONS155302p5GCh2728Sp OBJECT IDENTIFIER ::= { cevModuleONS15530Type 164 }
cevONS155302p5GCh2930Sp OBJECT IDENTIFIER ::= { cevModuleONS15530Type 165 }
cevONS155302p5GCh3132Sp OBJECT IDENTIFIER ::= { cevModuleONS15530Type 166 }
cevONS155302p5GCh0102 OBJECT IDENTIFIER ::= { cevModuleONS15530Type 167 }
cevONS155302p5GCh0304 OBJECT IDENTIFIER ::= { cevModuleONS15530Type 168 }
cevONS155302p5GCh0506 OBJECT IDENTIFIER ::= { cevModuleONS15530Type 169 }
cevONS155302p5GCh0708 OBJECT IDENTIFIER ::= { cevModuleONS15530Type 170 }
cevONS155302p5GCh0910 OBJECT IDENTIFIER ::= { cevModuleONS15530Type 171 }
cevONS155302p5GCh1112 OBJECT IDENTIFIER ::= { cevModuleONS15530Type 172 }
cevONS155302p5GCh1314 OBJECT IDENTIFIER ::= { cevModuleONS15530Type 173 }
cevONS155302p5GCh1516 OBJECT IDENTIFIER ::= { cevModuleONS15530Type 174 }
cevONS155302p5GCh1718 OBJECT IDENTIFIER ::= { cevModuleONS15530Type 175 }
cevONS155302p5GCh1920 OBJECT IDENTIFIER ::= { cevModuleONS15530Type 176 }
cevONS155302p5GCh2122 OBJECT IDENTIFIER ::= { cevModuleONS15530Type 177 }
cevONS155302p5GCh2324 OBJECT IDENTIFIER ::= { cevModuleONS15530Type 178 }
cevONS155302p5GCh2526 OBJECT IDENTIFIER ::= { cevModuleONS15530Type 179 }
cevONS155302p5GCh2728 OBJECT IDENTIFIER ::= { cevModuleONS15530Type 180 }
cevONS155302p5GCh2930 OBJECT IDENTIFIER ::= { cevModuleONS15530Type 181 }
cevONS155302p5GCh3132 OBJECT IDENTIFIER ::= { cevModuleONS15530Type 182 }
cevONS15530PSM  OBJECT IDENTIFIER ::= { cevModuleONS15530Type 183 }
cevModuleONS15500Type OBJECT IDENTIFIER ::= { cevModule 46 }
cevONS15500PEQ01A OBJECT IDENTIFIER ::= { cevModuleONS15500Type 1 }
cevONS15500PEQ01B OBJECT IDENTIFIER ::= { cevModuleONS15500Type 2 }
cevONS15500PEQ01C OBJECT IDENTIFIER ::= { cevModuleONS15500Type 3 }
cevONS15500PEQ01D OBJECT IDENTIFIER ::= { cevModuleONS15500Type 4 }
cevONS15500PEQ01E OBJECT IDENTIFIER ::= { cevModuleONS15500Type 5 }
cevONS15500PEQ01F OBJECT IDENTIFIER ::= { cevModuleONS15500Type 6 }
cevONS15500PEQ01G OBJECT IDENTIFIER ::= { cevModuleONS15500Type 7 }
cevONS15500PEQ01H OBJECT IDENTIFIER ::= { cevModuleONS15500Type 8 }
cevONS15500PEQ02AB OBJECT IDENTIFIER ::= { cevModuleONS15500Type 9 }
cevONS15500PEQ02CD OBJECT IDENTIFIER ::= { cevModuleONS15500Type 10 }
cevONS15500PEQ02EF OBJECT IDENTIFIER ::= { cevModuleONS15500Type 11 }
cevONS15500PEQ02GH OBJECT IDENTIFIER ::= { cevModuleONS15500Type 12 }
cevONS15500VOA01 OBJECT IDENTIFIER ::= { cevModuleONS15500Type 13 }
cevONS15500VOA02 OBJECT IDENTIFIER ::= { cevModuleONS15500Type 14 }
cevONS15500XvrEscon1310MTRJ OBJECT IDENTIFIER ::= { cevModuleONS15500Type 15 }
cevONS15500XvrEscon1310LC OBJECT IDENTIFIER ::= { cevModuleONS15500Type 16 }
cevONS15500XvrFC850LC OBJECT IDENTIFIER ::= { cevModuleONS15500Type 17 }
cevONS15500XvrFC850MTRJ OBJECT IDENTIFIER ::= { cevModuleONS15500Type 18 }
cevONS15500XvrFC1310LC OBJECT IDENTIFIER ::= { cevModuleONS15500Type 19 }
cevONS15500XvrFC1310MTRJ OBJECT IDENTIFIER ::= { cevModuleONS15500Type 20 }
cevONS15500XvrGE850LC OBJECT IDENTIFIER ::= { cevModuleONS15500Type 21 }
cevONS15500XvrGE850MTRJ OBJECT IDENTIFIER ::= { cevModuleONS15500Type 22 }
cevONS15500XvrGE1310LC OBJECT IDENTIFIER ::= { cevModuleONS15500Type 23 }
cevONS15500XvrGE1310MTRJ OBJECT IDENTIFIER ::= { cevModuleONS15500Type 24 }
cevONS15500XvrGEFC850LC OBJECT IDENTIFIER ::= { cevModuleONS15500Type 25 }
cevONS15500XvrGEFC850MTRJ OBJECT IDENTIFIER ::= { cevModuleONS15500Type 26 }
cevONS15500XvrGEFC1310LC OBJECT IDENTIFIER ::= { cevModuleONS15500Type 27 }
cevONS15500XvrGEFC1310MTRJ OBJECT IDENTIFIER ::= { cevModuleONS15500Type 28 }
cevONS15500XvrOC3Son1310MTRJ OBJECT IDENTIFIER ::= { cevModuleONS15500Type 29 }
cevONS15500XvrOC3Son1310LC OBJECT IDENTIFIER ::= { cevModuleONS15500Type 30 }
cevONS15500XvrOC12Son1310MTRJ OBJECT IDENTIFIER ::= { cevModuleONS15500Type 31 }
cevONS15500XvrOC12Son1310LC OBJECT IDENTIFIER ::= { cevModuleONS15500Type 32 }
cevONS15500XvrOC48Son1310MTRJ OBJECT IDENTIFIER ::= { cevModuleONS15500Type 33 }
cevONS15500XvrOC48Son1310LC OBJECT IDENTIFIER ::= { cevModuleONS15500Type 34 }
cevModuleC4224Type OBJECT IDENTIFIER ::= { cevModule 47 }
cevC42241FeTx   OBJECT IDENTIFIER ::= { cevModuleC4224Type 1 }
cevC422424FeTx  OBJECT IDENTIFIER ::= { cevModuleC4224Type 2 }
cevModuleSFPType OBJECT IDENTIFIER ::= { cevModule 51 }
cevModuleONS15200Type OBJECT IDENTIFIER ::= { cevModule 52 }
cevONS15252Clip OBJECT IDENTIFIER ::= { cevModuleONS15200Type 1 }
cevONS15201Clip OBJECT IDENTIFIER ::= { cevModuleONS15200Type 2 }
cevONS15252Ncb  OBJECT IDENTIFIER ::= { cevModuleONS15200Type 3 }
cevModuleMDSType OBJECT IDENTIFIER ::= { cevModule 53 }
cevMDSDsX9530Sf1K9 OBJECT IDENTIFIER ::= { cevModuleMDSType 1 }
cevMDSRedDsX9530Sf1K9 OBJECT IDENTIFIER ::= { cevModuleMDSType 2 }
cevMDSDsX9016   OBJECT IDENTIFIER ::= { cevModuleMDSType 3 }
cevMDSDsX9032   OBJECT IDENTIFIER ::= { cevModuleMDSType 4 }
cevMDSDsX9032Smv OBJECT IDENTIFIER ::= { cevModuleMDSType 5 }
cevMDSDsX9308Smip OBJECT IDENTIFIER ::= { cevModuleMDSType 6 }
cevMDSDsX9560Smap OBJECT IDENTIFIER ::= { cevModuleMDSType 7 }
cevMDSDsSfpFc2Gsw OBJECT IDENTIFIER ::= { cevModuleMDSType 8 }
cevMDSDsSfpFc2Glw OBJECT IDENTIFIER ::= { cevModuleMDSType 9 }
cevMDSDsSfpGeSw OBJECT IDENTIFIER ::= { cevModuleMDSType 10 }
cevMDSDsSfpGeLw OBJECT IDENTIFIER ::= { cevModuleMDSType 11 }
cevMDSDsC9500Cl OBJECT IDENTIFIER ::= { cevModuleMDSType 12 }
cevMDSDsX9216K9Sup OBJECT IDENTIFIER ::= { cevModuleMDSType 13 }
cevMDSMemFld512M OBJECT IDENTIFIER ::= { cevModuleMDSType 14 }
cevMDSMemMd1G   OBJECT IDENTIFIER ::= { cevModuleMDSType 15 }
cevMDSDsC9509Cl OBJECT IDENTIFIER ::= { cevModuleMDSType 16 }
cevMDSDsC9506Cl OBJECT IDENTIFIER ::= { cevModuleMDSType 17 }
cevPort         OBJECT IDENTIFIER ::= { cevMIBObjects 10 }
cevPortUnknown  OBJECT IDENTIFIER ::= { cevPort 1 }
cevPortMCIEther OBJECT IDENTIFIER ::= { cevPort 2 }
cevPortMCISerial OBJECT IDENTIFIER ::= { cevPort 3 }
cevPortCBusSerial OBJECT IDENTIFIER ::= { cevPort 4 }
cevPortFddi     OBJECT IDENTIFIER ::= { cevPort 5 }
cevPortFddit    OBJECT IDENTIFIER ::= { cevPort 6 }
cevPortCBusTR   OBJECT IDENTIFIER ::= { cevPort 7 }
cevPortAsync    OBJECT IDENTIFIER ::= { cevPort 8 }
cevPortHSSI     OBJECT IDENTIFIER ::= { cevPort 9 }
cevPortT1       OBJECT IDENTIFIER ::= { cevPort 10 }
cevPortE1       OBJECT IDENTIFIER ::= { cevPort 11 }
cevPortBRI      OBJECT IDENTIFIER ::= { cevPort 12 }
cevPortAIP      OBJECT IDENTIFIER ::= { cevPort 13 }
cevPortCIP      OBJECT IDENTIFIER ::= { cevPort 14 }
cevPortVtyAsync OBJECT IDENTIFIER ::= { cevPort 15 }
cevPortFEIP     OBJECT IDENTIFIER ::= { cevPort 16 }
cevPortAsyncGroup OBJECT IDENTIFIER ::= { cevPort 17 }
cevPortVTemplate OBJECT IDENTIFIER ::= { cevPort 18 }
cevPortVAccess  OBJECT IDENTIFIER ::= { cevPort 19 }
cevPortT3       OBJECT IDENTIFIER ::= { cevPort 20 }
cevPortVGAnyLAN OBJECT IDENTIFIER ::= { cevPort 21 }
cevPortLance    OBJECT IDENTIFIER ::= { cevPort 22 }
cevPortATMS2000 OBJECT IDENTIFIER ::= { cevPort 23 }
cevPortSALI25   OBJECT IDENTIFIER ::= { cevPort 24 }
cevPortSonicT   OBJECT IDENTIFIER ::= { cevPort 25 }
cevPortOC3SUNI  OBJECT IDENTIFIER ::= { cevPort 26 }
cevPortOC12SUNI OBJECT IDENTIFIER ::= { cevPort 27 }
cevPortDS3SUNI  OBJECT IDENTIFIER ::= { cevPort 28 }
cevPortE3SUNI   OBJECT IDENTIFIER ::= { cevPort 29 }
cevPortDS3SUNIQUAD OBJECT IDENTIFIER ::= { cevPort 30 }
cevPortE3SUNIQUAD OBJECT IDENTIFIER ::= { cevPort 31 }
cevPortMK5025   OBJECT IDENTIFIER ::= { cevPort 32 }
cevPortTMS380   OBJECT IDENTIFIER ::= { cevPort 33 }
cevPortBSI      OBJECT IDENTIFIER ::= { cevPort 34 }
cevPortATMZR    OBJECT IDENTIFIER ::= { cevPort 35 }
cevPortHD64570  OBJECT IDENTIFIER ::= { cevPort 36 }
cevPortPCBus    OBJECT IDENTIFIER ::= { cevPort 37 }
cevPortQuiccEther OBJECT IDENTIFIER ::= { cevPort 38 }
cevPortQuiccSerial OBJECT IDENTIFIER ::= { cevPort 39 }
cevPortAMDP2    OBJECT IDENTIFIER ::= { cevPort 40 }
cevPortMIF68840 OBJECT IDENTIFIER ::= { cevPort 41 }
cevPortCYLEPA   OBJECT IDENTIFIER ::= { cevPort 42 }
cevPortS4T68360 OBJECT IDENTIFIER ::= { cevPort 43 }
cevPortIBM2692  OBJECT IDENTIFIER ::= { cevPort 44 }
cevPortMueslix  OBJECT IDENTIFIER ::= { cevPort 45 }
cevPortCD2430   OBJECT IDENTIFIER ::= { cevPort 46 }
cevPortILACC    OBJECT IDENTIFIER ::= { cevPort 47 }
cevPortNIC100   OBJECT IDENTIFIER ::= { cevPort 48 }
cevPortDCUATM   OBJECT IDENTIFIER ::= { cevPort 49 }
cevPortDCUATMPort OBJECT IDENTIFIER ::= { cevPort 50 }
cevPortTI1570   OBJECT IDENTIFIER ::= { cevPort 51 }
cevPortPOS      OBJECT IDENTIFIER ::= { cevPort 52 }
cevPortLoopBack OBJECT IDENTIFIER ::= { cevPort 53 }
cevPortLex      OBJECT IDENTIFIER ::= { cevPort 54 }
cevPortDialer   OBJECT IDENTIFIER ::= { cevPort 55 }
cevPortCIPLANAdapter OBJECT IDENTIFIER ::= { cevPort 56 }
cevPortBVI      OBJECT IDENTIFIER ::= { cevPort 57 }
cevPortOSPFVL   OBJECT IDENTIFIER ::= { cevPort 58 }
cevPortRinconSwitch OBJECT IDENTIFIER ::= { cevPort 59 }
cevPortSynALCATM OBJECT IDENTIFIER ::= { cevPort 60 }
cevPortSynALCBIGA OBJECT IDENTIFIER ::= { cevPort 61 }
cevPortSwitchTrunk OBJECT IDENTIFIER ::= { cevPort 62 }
cevPortC2KATM   OBJECT IDENTIFIER ::= { cevPort 63 }
cevPortDec21140A OBJECT IDENTIFIER ::= { cevPort 64 }
cevPortC5Ether  OBJECT IDENTIFIER ::= { cevPort 65 }
cevPortC5TR     OBJECT IDENTIFIER ::= { cevPort 66 }
cevPortEswitch  OBJECT IDENTIFIER ::= { cevPort 69 }
cevPortBITS     OBJECT IDENTIFIER ::= { cevPort 70 }
cevPortAdslCap  OBJECT IDENTIFIER ::= { cevPort 71 }
cevPortAdslDmt  OBJECT IDENTIFIER ::= { cevPort 72 }
cevPortSdsl2b1q OBJECT IDENTIFIER ::= { cevPort 73 }
cevPortEscon    OBJECT IDENTIFIER ::= { cevPort 74 }
cevPortParallel OBJECT IDENTIFIER ::= { cevPort 75 }
cevPortCipVirtual OBJECT IDENTIFIER ::= { cevPort 76 }
cevPortDs3      OBJECT IDENTIFIER ::= { cevPort 78 }
cevPortE3       OBJECT IDENTIFIER ::= { cevPort 79 }
cevPortOc3      OBJECT IDENTIFIER ::= { cevPort 80 }
cevPortHdvDsp   OBJECT IDENTIFIER ::= { cevPort 82 }
cevPortRfMac    OBJECT IDENTIFIER ::= { cevPort 86 }
cevPortRfUs     OBJECT IDENTIFIER ::= { cevPort 87 }
cevPortRfDs     OBJECT IDENTIFIER ::= { cevPort 88 }
cevPortUbrClk   OBJECT IDENTIFIER ::= { cevPort 89 }
cevPortWDM      OBJECT IDENTIFIER ::= { cevPort 101 }
cevPortThru     OBJECT IDENTIFIER ::= { cevPort 102 }
cevPortFilter   OBJECT IDENTIFIER ::= { cevPort 103 }
cevPortWave     OBJECT IDENTIFIER ::= { cevPort 104 }
cevPortWavePatch OBJECT IDENTIFIER ::= { cevPort 105 }
cevPortTransparent OBJECT IDENTIFIER ::= { cevPort 106 }
cevPortDPT      OBJECT IDENTIFIER ::= { cevPort 107 }
cevPortOc12     OBJECT IDENTIFIER ::= { cevPort 108 }
cevPortGe       OBJECT IDENTIFIER ::= { cevPort 109 }
cevPortChOc12   OBJECT IDENTIFIER ::= { cevPort 110 }
cevPortChOc3Stm1 OBJECT IDENTIFIER ::= { cevPort 111 }
cevPortFilterGroup OBJECT IDENTIFIER ::= { cevPort 112 }
cevPortFilterBand OBJECT IDENTIFIER ::= { cevPort 113 }
cevPortChE1T1   OBJECT IDENTIFIER ::= { cevPort 114 }
cevPortASIMod   OBJECT IDENTIFIER ::= { cevPort 115 }
cevPortASIIn    OBJECT IDENTIFIER ::= { cevPort 116 }
cevPortASIOut   OBJECT IDENTIFIER ::= { cevPort 117 }
cevPortAimDsp   OBJECT IDENTIFIER ::= { cevPort 118 }
cevPortFxs      OBJECT IDENTIFIER ::= { cevPort 126 }
cevPortFxo      OBJECT IDENTIFIER ::= { cevPort 127 }
cevPortEM       OBJECT IDENTIFIER ::= { cevPort 128 }
cevPortOc48     OBJECT IDENTIFIER ::= { cevPort 129 }
cevPortOc192    OBJECT IDENTIFIER ::= { cevPort 130 }
cevPortFibreChannel OBJECT IDENTIFIER ::= { cevPort 131 }
cevPortGigEthernet OBJECT IDENTIFIER ::= { cevPort 132 }
cevPortFibreChGigEth OBJECT IDENTIFIER ::= { cevPort 133 }
cevPortWaveOsc  OBJECT IDENTIFIER ::= { cevPort 135 }
cevPortWaveEthPhy OBJECT IDENTIFIER ::= { cevPort 136 }
cevPort10GigEthPhy OBJECT IDENTIFIER ::= { cevPort 137 }
cevPortEsconPhy OBJECT IDENTIFIER ::= { cevPort 138 }
cevPortGEFCPhy  OBJECT IDENTIFIER ::= { cevPort 139 }
cevPortVOAIn    OBJECT IDENTIFIER ::= { cevPort 140 }
cevPortVOAOut   OBJECT IDENTIFIER ::= { cevPort 141 }
cevPortVOAFilterIn OBJECT IDENTIFIER ::= { cevPort 142 }
cevPortVOAFilterOut OBJECT IDENTIFIER ::= { cevPort 143 }
cevPortVOAByPassIn OBJECT IDENTIFIER ::= { cevPort 144 }
cevPortVOAByPassOut OBJECT IDENTIFIER ::= { cevPort 145 }
cevPortGT96K    OBJECT IDENTIFIER ::= { cevPort 146 }
cevPortDSCC4    OBJECT IDENTIFIER ::= { cevPort 147 }
cevPortWdmSplit OBJECT IDENTIFIER ::= { cevPort 152 }
cevPortWavePassThru OBJECT IDENTIFIER ::= { cevPort 153 }
cevPortDspPVDM  OBJECT IDENTIFIER ::= { cevPort 154 }
cevPortiScsi    OBJECT IDENTIFIER ::= { cevPort 155 }


END
